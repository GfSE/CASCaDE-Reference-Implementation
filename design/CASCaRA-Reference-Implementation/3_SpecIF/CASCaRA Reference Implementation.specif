# CASCaRA Reference Implementation
This is the concept and design of the CASCaRA App which is a reference implementation used to validate the standard in preparation. 

The model gives an overview of the use-cases and the architecture, whereas further details are developed via [GitHub issues](https://github.com/GfSE/CASCaDE-Reference-Implementation/issues). The planning is done with a [GitHub project](https://github.com/orgs/GfSE/projects/5/views/1). 

[CASCaRA](https://cascara.gfse.org) is a project to standardize collaboration in systems engineering with respect to data format and ontology. A [Request for Proposal (RFP)](https://www.omg.org/cgi-bin/doc?mantis/24-12-03.pdf) has been accepted by OMG in December 2024. Information in different formats and from diverse sources are transformed and integrated to a common knowledge graph.

A publicly available reference implementation shall validate the concepts of the standard as developed by the CASCaRA submission team. Validation is successful, if real-world data is ingested and the information needs of all users in the product lifecycle are met. Users and software vendors are given the opportunity to influence the project to assure their ideas are taken aboard. A joint effort on fundamental features (where differentiation isn't possible anyways) avoids duplicate work, improves quality and assures interoperability.

The reference implementation addresses the following aspects:
- Check data format and constraints according to the [CASCaRA Metamodel](https://product-information-graph.org/doc/metamodel/latest/) to assure data quality. 
- Persistently store and retrieve CASCaRA Graph data using the standardized API (to be defined).
- View and edit CASCaRA data in a web-browser.
- Transform input data with the formats ReqIF, SysML v1 and v2, STEP and FMI/SSP. Other input formats may follow.
- Integrate input data with different formats to an interwoven knowledge graph.
- Create output data with the formats RDF/Turtle, JSON-LD and XHTML.
- Provide a set of *standard queries* ('competency questions') that work for all data complying with the meta-model.
- Bring the data into a standardized form to facilitate machine learning and AI applications.

Major requirements (capabilities and characteristics) must be satisfied:
- **Separation of Concerns**: Syntax and Semantics are separated, so that no software updates are needed, when the ontology evolves over time.
- **Design for transformation**: The CASCaRA Metamodel (‘magic tetrahedron’) assures loss-less transformation between RDF/OWL (Knowledge Graphs), GQL (Property Graphs) and Object-oriented Programming.
- **Federation**: RDF and JSON-LD support dataspaces with federated data under full control of the respective owners.
- **Multi-Format Support**: JSON-LD, XML, RDF/Turtle and GQL/Cypher supporting in a wide range of technologies.
- Comply with web-technology and avoid proprietary formats.
- Extend the software using a documented, if possible standardized plug-in mechanism.

This model is authored with [Archi](https://www.archimatetool.com/) using the ArchiMate 3.2 notation, then transformed to [SpecIF](https://specif.de) via ArchiMate Open Exchange file format and then transformed to HTML. The CASCaRA App will support a similar workflow (among others) for the source data formats chosen.
- Rights: Creative Commons 4.0 CC BY-SA, https://creativecommons.org/licenses/by-sa/4.0/

## CASCaRA Reference Implementation (SpecIF:Heading)
- dcterms:description: This is the concept and design of the CASCaRA App which is a reference implementation used to validate the standard in preparation. 

  The model gives an overview of the use-cases and the architecture, whereas further details are developed via [GitHub issues](https://github.com/GfSE/CASCaDE-Reference-Implementation/issues). The planning is done with a [GitHub project](https://github.com/orgs/GfSE/projects/5/views/1). 

  [CASCaRA](https://cascara.gfse.org) is a project to standardize collaboration in systems engineering with respect to data format and ontology. A [Request for Proposal (RFP)](https://www.omg.org/cgi-bin/doc?mantis/24-12-03.pdf) has been accepted by OMG in December 2024. Information in different formats and from diverse sources are transformed and integrated to a common knowledge graph.

  A publicly available reference implementation shall validate the concepts of the standard as developed by the CASCaRA submission team. Validation is successful, if real-world data is ingested and the information needs of all users in the product lifecycle are met. Users and software vendors are given the opportunity to influence the project to assure their ideas are taken aboard. A joint effort on fundamental features (where differentiation isn't possible anyways) avoids duplicate work, improves quality and assures interoperability.

  The reference implementation addresses the following aspects:
  - Check data format and constraints according to the [CASCaRA Metamodel](https://product-information-graph.org/doc/metamodel/latest/) to assure data quality. 
  - Persistently store and retrieve CASCaRA Graph data using the standardized API (to be defined).
  - View and edit CASCaRA data in a web-browser.
  - Transform input data with the formats ReqIF, SysML v1 and v2, STEP and FMI/SSP. Other input formats may follow.
  - Integrate input data with different formats to an interwoven knowledge graph.
  - Create output data with the formats RDF/Turtle, JSON-LD and XHTML.
  - Provide a set of *standard queries* ('competency questions') that work for all data complying with the meta-model.
  - Bring the data into a standardized form to facilitate machine learning and AI applications.

  Major requirements (capabilities and characteristics) must be satisfied:
  - **Separation of Concerns**: Syntax and Semantics are separated, so that no software updates are needed, when the ontology evolves over time.
  - **Design for transformation**: The CASCaRA Metamodel (‘magic tetrahedron’) assures loss-less transformation between RDF/OWL (Knowledge Graphs), GQL (Property Graphs) and Object-oriented Programming.
  - **Federation**: RDF and JSON-LD support dataspaces with federated data under full control of the respective owners.
  - **Multi-Format Support**: JSON-LD, XML, RDF/Turtle and GQL/Cypher supporting in a wide range of technologies.
  - Comply with web-technology and avoid proprietary formats.
  - Extend the software using a documented, if possible standardized plug-in mechanism.

  This model is authored with [Archi](https://www.archimatetool.com/) using the ArchiMate 3.2 notation, then transformed to [SpecIF](https://specif.de) via ArchiMate Open Exchange file format and then transformed to HTML. The CASCaRA App will support a similar workflow (among others) for the source data formats chosen.
- dcterms:type: SpecIF:Outline

## SpecIF:Views (SpecIF:Heading)

## Validation Process (SpecIF:Heading)
- dcterms:type: SpecIF:Heading

## Validation Process (cas:View)
- dcterms:description: A process to validate the conceptual and technical choices made by the standard in preparation. This is preliminary and needs further discussion and detailing with the target users. Ultimately, the standard must satisfy their use-cases and needs in general.

  Subject to validation:
  - Has the [CASCaRA Metamodel](https://product-information-graph.org/doc/metamodel/latest/) enough expressive power to deal with real-world data?
  - Can the data be transformed between RDF/Turtle, JSON-LD and GQL without loss? In all directions and in a full round-trip?
  - Are the transformation results consistent, complete, comprehensible and finally useful?
  - Can the user's 'competency questions' be satisfactorily answered?
- cas:Diagram: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
- dcterms:type: ArchiMate:Viewpoint
- cas:Notation: Application Usage

## Module Architecture (SpecIF:Heading)
- dcterms:type: SpecIF:Heading

## App (cas:View)
- dcterms:description: The top-level module architecture of the CASCaRA App embedded in its system context.
- cas:Diagram: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
- dcterms:type: ArchiMate:Viewpoint
- cas:Notation: Application Structure

## Server (cas:View)
- dcterms:description: The module architecture of a CASCaRA Server for collaboration along the product lifecycle and as a standardized knowledge base for AI.
- cas:Diagram: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
- dcterms:type: ArchiMate:Viewpoint
- cas:Notation: Application Cooperation

## Import Processing (cas:View)
- dcterms:description: Different paths of import processing of the [[CASCaRA App]] are shown. They correspond to the edges of the Magic Tetrahedron, which defines the sweet spot where round-trip transformations between RDF, JSON-LD, Object-oriented Data and GQL are possible without loss of information.

  The input formats defined have different purpose or strength:

  | Category | Format | Purpose and Strength |
  | --- | --- | ---|
  | Processing | OO Classes | Data Processing, Version and Configuration Management, Multi-user Operation |
  | Processing | .json| Equivalent with the above for schema checking, storage |
  | Exchange | .cas.jsonld | Higher level graph language for API and LD-Processors: Entities and relationships as self-contained objects with URI, standardized type and designated values, explicit, easy to transform |
  | Exchange | .cas.xml | Equivalent with the above for users preferring the XML ecosystem |
  | Knowledge Graph | .cas.ttl | For use in the RDF/OWL ecosystem: Triple-Stores, SPARQL, SHACL, reasoning, visualization, elegant, compact, needs reasoning to uncover implicit meaning, low level graph („Graph Assembly Language“) |
  | Knowledge Graph | .jsonld | Not planned, as it is redundant with the above |
  | Knowledge Graph | .xml | Not planned, either |
  | Property Graph | .gql, .cyp | For use in the ecosystem of Labelled Property Graphs: Graph Databases, superior performance, visualization |
- cas:Diagram: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
- dcterms:type: ArchiMate:Viewpoint
- cas:Notation: Application Usage

## Configuration Options (SpecIF:Heading)
- dcterms:type: SpecIF:Heading

## Configuration Options (cas:View)
- cas:Diagram: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
- dcterms:type: ArchiMate:Viewpoint

## Model Elements (Glossary) (SpecIF:Heading)
- dcterms:type: SpecIF:Glossary

## 2-Layer Client-Server (SpecIF:Collection)
- dcterms:description: A server consists of CASCaRA code accessing a (graph) database in the same container or even on the same virtual machine. One or more browser apps can access the server concurrently.
- dcterms:type: ArchiMate:Grouping

## 3-Layer Client-Server (SpecIF:Collection)
- dcterms:description: A server consists of CASCaRA code accessing a (graph) database in a separate container. One or more browser apps can access the server concurrently. When compared with the [[2-Layer Client-Server]] scheme, this configuration has the advantage of being easier to update in a production environment at the cost of a somewhat inferior performance.
- dcterms:type: ArchiMate:Grouping

## any-to-cas.mvf (FMC:State)
- dcterms:description: The data for the Multi-Vocabulary-Facility (MVF). It contains multiple vocabularies in domain and national languages plus standardized terms called 'concepts' with their synonym and antonym relationships. The concepts correspond to the classes of the CASCaRA Ontology. The relationships can be used for any-to-cas matching as well as the inverse.
- dcterms:type: ArchiMate:DataObject

## any-to-cas.sparql (FMC:State)
- dcterms:description: A set of SPARQL Protocol and RDF Query Language queries to extract relevant information from RDF data having a pattern conforming with the [CASCARA Metamodel](https://product-information-graph.org/doc/metamodel/latest/).
- dcterms:type: ArchiMate:DataObject

## API4KP (FMC:Actor)
- dcterms:description: Implements a REST API as designed in [APIs for Knowledge Platforms - API4KP](https://www.omg.org/spec/API4KP/1.0/About-API4KP).
- dcterms:type: ArchiMate:ApplicationInterface

## Apply Competency Question (FMC:Actor)
- dcterms:description: Once transformed to RDF/Turtle, still according to the [CASCaRA Metamodel](https://product-information-graph.org/doc/metamodel/latest/), user-defined competency questions shall be applied to the test-data. Those queries shall validate that the graph fulfills the information needs of the various user roles accessing the data. An important criterion is that the _same_ (i.e. standard) queries yield the desired results with data from different sources. Only then, normalization with respect to syntax and semantics is successful. It is expected, however, that the competency questions (the queries) depend on the ontology with the the current set of *preferred terms*.
- dcterms:type: ArchiMate:BusinessProcess

## Assign Ontology Class (FMC:Actor)
- dcterms:description: Input data compliant with the [CASCARA Metamodel](https://product-information-graph.org/doc/metamodel/latest/) are matched with the CASCaRA Ontology using a [[MVF Engine]] using the synonyms and antonyms defined in [[any-to-cas.mvf]].
- dcterms:type: ArchiMate:ApplicationFunction

## Business Use-Case (FMC:State)
- dcterms:description: A set of use-cases describing the user's need. Must be exemplary (concrete), relevant and representative.
- dcterms:type: ArchiMate:BusinessObject

## Cache (FMC:State)
- dcterms:type: ArchiMate:DataObject

## CASCaRA API (FMC:Actor)
- dcterms:description: Extends the methods of the [[Common Lib]] to a ReST API.
- dcterms:type: ArchiMate:ApplicationInterface

## CASCaRA App (FMC:Actor)
- dcterms:description: A web application for creating, reading, updating and deleting data elements. The app is configured by the classes loaded at initialization time. The classes govern the choice and the dialog layout for modifying the data. Thus, the same software is used for more or less complex applications. 

  The architecture includes a plugin mechanism to allow the deployment of new transformations or storage adapters without building and deploying a complete new image, for details see ['Design Plugin Mechanism'](https://github.com/GfSE/CASCaDE-Reference-Implementation/issues/21).

  A major challenge is an optimal design of the programming class structure ('scaffold'), the representation in JSON-LD, RDF/Turtle and GQL according to the [CASCaRA Metamodel](https://product-information-graph.org/doc/metamodel/latest/). Goal is to allow loss-less transformations between all representations. For details see [Optimize the 'magic tetrahedron'](https://github.com/GfSE/CASCaDE-Reference-Implementation/issues/22).

  Details of the development, build, integration and deployment environment are discussed in ['Select Development Environment and Programming Language'](https://github.com/GfSE/CASCaDE-Reference-Implementation/issues/14).

  Further aspects:
  - Reporting Interface (e.g. Power-BI), server-side per API or client-side per file (export plugin).
  - Permission Management
- dcterms:type: ArchiMate:ApplicationComponent

## CASCaRA Graph (FMC:State)
- dcterms:description: The CASCaRA Graph integrating partial information from different sources. It complies with the [CASCARA Metamodel](https://product-information-graph.org/doc/metamodel/latest/).
- dcterms:type: ArchiMate:BusinessObject

## CASCaRA Server (FMC:Actor)
- dcterms:description: A server-side IT application that may serve as a collaboration hub along the product lifecycle and as a standardized knowledge base for AI. Integrated product information is shared as a graph with create, read, update and delete function for individual nodes (entities) and edges (relationships) as well as packages containing a certain sub-graph. The [CASCaRA Metamodel](https://product-information-graph.org/doc/metamodel/latest/) defines the graph structure. Import formats are .cas.ttl, .cas.jsonld and .cas.xml. Any .xml file can be imported, if a XSL stylesheet is provided for transformation to .cas.xml. Export formats are .cas.ttl, .cas.jsonld, .cas.xml and .html.
- dcterms:type: ArchiMate:ApplicationComponent

## CASCaRA Server Adapter (FMC:Actor)
- dcterms:type: ArchiMate:ApplicationComponent

## CASCaRA Validation Process (FMC:Actor)
- dcterms:type: ArchiMate:BusinessProcess

## Check CASCaRA JSON Schema (FMC:Actor)
- dcterms:description: The subgraph with assigned ontology classes is checked to comply with the [CASCARA Metamodel](https://product-information-graph.org/doc/metamodel/latest/).
- dcterms:type: ArchiMate:ApplicationFunction

## Check CASCaRA JSON-LD Schema (FMC:Actor)
- dcterms:description: Check input data with the [CASCaRA JSON-LD Schemata](https://product-information-graph.org/schema/latest/jsonld/).
- dcterms:type: ArchiMate:ApplicationFunction

## Check CASCaRA XML Schema (FMC:Actor)
- dcterms:description: Check input data with the CASCaRA XML Schemata.
- dcterms:type: ArchiMate:ApplicationFunction

## Check Package Constraints (FMC:Actor)
- dcterms:description: Package constraints are checked such as:
  - Uniqueness of identifiers
  - Availability of referenced classes
  - Conformance with referenced classes
  - Completeness of namespace definitions
  - and many more.
- dcterms:type: ArchiMate:ApplicationFunction

## Check Schema, Consistency and Completeness (FMC:Actor)
- dcterms:description: Once transformed according to the CASCaRA Metamodel, the data shall be checked with respect to schema (shape, format), consistency (constraints) and completeness. Both formally and by expert inspection.
- dcterms:type: ArchiMate:BusinessProcess

## Common Lib (FMC:Actor)
- dcterms:description: Shared by different CASCaRA Deployment Packages such as Browser App and Server.

  Offers the following functions:
  - graph cache with setters and getters
  - [[XSLT Engine]], [[SPARQL Engine]], [[MVF Engine]] and [[JSON Schema Engine]]
  - import transformations from cas.jsonld, cas.xml and cas.ttl
  - export transformations to cas.jsonld, cas.xml, cas.ttl and HTML
- dcterms:type: ArchiMate:ApplicationComponent

## Configuration Data (FMC:State)
- dcterms:type: ArchiMate:DataObject

## Controller (FMC:Actor)
- dcterms:description: The controller is the 'main' component and is in charge of managing the execution of requested services in reaction on user or server events. In the easiest case ES promises are used and the scheduling is left to the event queuing of the execution environment. But certain services may require coordination or user feedback (via spinner or log message, for example). So it is the responsibility of the controller to enable and disable elements creating events to maintain the integrity of the app and the data.

  Is usually provided by the application framework. An option is to implement an event dispatcher controlled by a state-machine.
- dcterms:type: ArchiMate:ApplicationComponent

## Create CASCaRA Subgraph (FMC:Actor)
- dcterms:description: Input information as provided by various authoring tools often comes in hierarchical order. Whatever the input format is, it is transformed to a subgraph complying with the [CASCARA Metamodel](https://product-information-graph.org/doc/metamodel/latest/).
- dcterms:type: ArchiMate:BusinessFunction

## Create Test-Data (FMC:Actor)
- dcterms:description: Create test-data in original format as produced by popular authoring systems of the domain, for example IBM DOORS for requirement management or Cameo for systems engineering.

  Initially, test-data should be small and cover relevant and typical aspects of the domain to drive and validate the development of transformations. Later on, real or near-real project data 'from the field' with growing complexity should be supplied.
- dcterms:type: ArchiMate:BusinessProcess

## data.cas.jsonld (FMC:State)
- dcterms:type: ArchiMate:DataObject

## Document-DB Storage Adapter (FMC:Actor)
- dcterms:description: Interfaces a document database, either embedded or in an external container.
- dcterms:type: ArchiMate:ApplicationComponent

## Export Adapter (FMC:Actor)
- dcterms:description: Transforms a selected subgraph from the internal data format according to the CASCaRA Metamodel to a desired output format.

  The following transformations are planned for validating the approach (i.e. the standard to submit):
  - [JSON-LD](https://github.com/GfSE/CASCaDE-Reference-Implementation/issues/27)
  - [RDF/Turtle](https://github.com/GfSE/CASCaDE-Reference-Implementation/issues/28)
  - [HTML](https://github.com/GfSE/CASCaDE-Reference-Implementation/issues/29)
  - [LOTAR](https://github.com/GfSE/CASCaDE-Reference-Implementation/issues/30)
- dcterms:type: ArchiMate:ApplicationComponent

## File System (FMC:Actor)
- dcterms:description: A network file system. Consider to use
  - Windows/MacOS/Linux NFS
  - Samba
  - Git
- dcterms:type: ArchiMate:ApplicationComponent

## FS Storage Adapter (FMC:Actor)
- dcterms:description: Store a subgraph in or retrieve it from a file system.
- dcterms:type: ArchiMate:ApplicationComponent

## Graph (FMC:State)
- dcterms:description: The CASCaRA Graph integrating partial information from different sources. It complies with the [CASCARA Metamodel](https://product-information-graph.org/doc/metamodel/latest/).
- dcterms:type: ArchiMate:DataObject

## Graph Database (FMC:State)
- dcterms:type: ArchiMate:DataObject

## Graph-DB Server (FMC:Actor)
- dcterms:description: A container with a standard Graph Database, alternatively a Document Database.
- dcterms:type: ArchiMate:ApplicationComponent

## Graph-DB Storage Adapter (FMC:Actor)
- dcterms:description: Interfaces a graph database, either embedded or in an external container.
- dcterms:type: ArchiMate:ApplicationComponent

## Import Adapter (FMC:Actor)
- dcterms:description: Transforms a source data format to the internal data format according to the [CASCaRA Metamodel](https://product-information-graph.org/doc/metamodel/latest/). A full transformation of the source data may not be necessary for the given use-cases, so emphasis is put on the *relevant* entities and relationships of the source data.

  Transformations may use:
  - XSLT in case of XML source data
  - SPARQL in case of RDF source data
  - Scripting

  The following transformations are planned for validating the approach (the standard to submit):
  - [ReqIF](https://github.com/GfSE/CASCaDE-Reference-Implementation/issues/25)
  - [SysML v1](https://github.com/GfSE/CASCaDE-Reference-Implementation/issues/26)
  - [STEP](https://github.com/GfSE/CASCaDE-Reference-Implementation/issues/4)
  - [FMI/SSP](https://github.com/GfSE/CASCaDE-Reference-Implementation/issues/7)
  - [LOTAR](https://github.com/GfSE/CASCaDE-Reference-Implementation/issues/6)
  - ...
- dcterms:type: ArchiMate:ApplicationComponent

## input.cas.jsonld (FMC:State)
- dcterms:description: Input data in XML format. A pattern compatible with the CASCaRA Metamodel is assumed. More precisely: It must comply with the [CASCaRA JSON-LD Schemata](https://product-information-graph.org/schema/latest/jsonld/).

  See example files:
  - [Alice works for ACME](https://github.com/GfSE/CASCaDE-Verification-and-Validation/blob/main/Alice%20%5BCASCaRA%20native%5D/6_JSONLD/Alice.cas.jsonld)
  - [Very Simple Model with Requirements (FMC)](https://github.com/GfSE/CASCaDE-Verification-and-Validation/blob/main/Very-simple-Model-with-Requirements%20%5BFMC%20-%20SpecIF%5D/6_JSONLD/Project%20'Very%20Simple%20Model%20(FMC)%20with%20Requirements'.cas.jsonld)
- dcterms:type: ArchiMate:DataObject

## input.cas.ttl (FMC:State)
- dcterms:description: Input data in RDF Turtle format. A pattern compatible with the CASCaRA Metamodel is assumed to fully interpret the data. 

  See example files:
  - [Alice works for ACME](https://github.com/GfSE/CASCaDE-Verification-and-Validation/blob/main/Alice%20%5BCASCaRA%20native%5D/7_RDF/Alice.cas.ttl)
  - [Very Simple Model with Requirements (FMC)](https://github.com/GfSE/CASCaDE-Verification-and-Validation/blob/main/Very-simple-Model-with-Requirements%20%5BFMC%20-%20SpecIF%5D/7_RDF/Project%20'Very%20Simple%20Model%20(FMC)%20with%20Requirements'.cas.ttl)
- dcterms:type: ArchiMate:DataObject

## input.cas.xml (FMC:State)
- dcterms:description: Input data in XML format. A pattern compatible with the CASCaRA Metamodel is assumed. 

  See example files:
  - [Alice works for ACME](https://github.com/GfSE/CASCaDE-Verification-and-Validation/blob/main/Alice%20%5BCASCaRA%20native%5D/5_XML/Alice.cas.xml)
  - [Very Simple Model with Requirements (FMC)](https://github.com/GfSE/CASCaDE-Verification-and-Validation/blob/main/Very-simple-Model-with-Requirements%20%5BFMC%20-%20SpecIF%5D/5_XML/Project%20'Very%20Simple%20Model%20(FMC)%20with%20Requirements'.cas.xml)
- dcterms:type: ArchiMate:DataObject

## input.reqif (FMC:State)
- dcterms:description: Input data in ReqIF format. It is assumed that it complies with the OMG Standard [Requirements Interchange Format (ReqIF)](https://www.omg.org/reqif/) and with the Prostep ivip [Implementation Guideline ReqIF](https://www.prostep.org/shop/detail?ai%5Baction%5D=detail&ai%5Bcontroller%5D=Catalog&ai%5Bd_name%5D=reqif_ig_v1-7&ai%5Bd_pos%5D=).
- dcterms:type: ArchiMate:DataObject

## Integrate Subgraph (FMC:Actor)
- dcterms:description: The final subgraph is integrated in the common [[Graph]], so that data from different sources in various formats can be analysed in a common context. It is used for display, exchange and reference by other applications including AI agents.
- dcterms:type: ArchiMate:ApplicationFunction

## itemType.json (FMC:State)
- dcterms:description: [JSON Schema](https://json-schema.org/) declaration per [CASCARA Metamodel](https://product-information-graph.org/doc/metamodel/latest/) item type, i.e. every block on the metamodel diagram. The latest CASCaRA schema files are published [here](https://product-information-graph.org/schema/latest/jsonld/). The web-service is CORS enabled, thus the schema files can be retrieved from any other web domain.
- dcterms:type: ArchiMate:DataObject

## JSON Schema Engine (FMC:Actor)
- dcterms:description: An engine checking a JSON or JSON-LD data set using [JSON Schema](https://json-schema.org/) declarations per CASCaRA Metamodel item type, see [[itemType.json]].
- dcterms:type: ArchiMate:ApplicationService

## Knowledge File (FMC:State)
- dcterms:description: A subgraph represented as RDF/Turtle or JSON-LD.
- dcterms:type: ArchiMate:DataObject

## Knowledge Platform (FMC:Actor)
- dcterms:description: Consider to use a backend with:
  - API4KP Knowledge Artifact Repository API
  - API4KP Knowledge Asset Repository API
- dcterms:type: ArchiMate:ApplicationComponent

## KP Storage Adapter (FMC:Actor)
- dcterms:description: Store a subgraph in or retrieve it from a knowledge platform.
- dcterms:type: ArchiMate:ApplicationComponent

## MCP API (FMC:Actor)
- dcterms:description: A Model Context Protocol (MCP) API is an interface designed to manage and exchange context information between AI models, agents, or services. Its main purpose is to standardize how context—such as user intent, conversation history, environment variables, or task state—is represented, shared, and updated during interactions with or between AI systems.

  Key features of a Model Context Protocol API:
  - Context Representation: Defines a structured format (often JSON or similar) for context data relevant to AI models.
  - Context Exchange: Provides endpoints or methods to retrieve, update, and synchronize context between clients, models, and other services.
  - Session Management: Supports tracking and managing context across sessions or conversations.
  - Interoperability: Ensures that different models or agents can understand and use shared context, enabling more coherent and personalized AI behavior.
  - Extensibility: Allows for custom context fields or domain-specific extensions.

  Typical use cases:
  - Maintaining conversation state in chatbots or virtual assistants.
  - Sharing user preferences or history between multiple AI services.
  - Coordinating multi-step reasoning or workflows across several models.

  Source: GitHub Copilot.
- dcterms:type: ArchiMate:ApplicationInterface

## Model Integration Plugin (FMC:Actor)
- dcterms:description: Integrates a new subgraph with the existing graph, e.g. by combining nodes representing the 'same' artifact. Two artefacts are considered the same, if class and title are equal. A preliminary decision has been taken to keep the original nodes and to create an 'umbrella' node pointing to two or more nodes of the same artifact.
- dcterms:type: ArchiMate:ApplicationComponent

## MVF Engine (FMC:Actor)
- dcterms:description: A Multi-Vocabulary-Facility mapping terms of multiple domain languages to the CASCaRA ontology terms and vice versa. The OMG Standard [Multiple Vocabulary Facility (MVF)](https://www.omg.org/spec/MVF/1.0/About-MVF) is partially implemented for that purpose.
- dcterms:type: ArchiMate:ApplicationService

## Ontology Plugin (FMC:Actor)
- dcterms:description: The ontology plugin provides services such as [[Assign Ontology Class]].
- dcterms:type: ArchiMate:ApplicationComponent

## Original Authoring System (FMC:Actor)
- dcterms:description: A system to create and maintain information somewhere in the product lifecycle. For example IBM DOORS for requirements management or Dassault Cameo for systems engineering.
- dcterms:type: ArchiMate:ApplicationComponent

## Other Storage Adapter (FMC:Actor)
- dcterms:description: Store a subgraph in or retrieve it from any other storage system as required.
- dcterms:type: ArchiMate:ApplicationComponent

## Partial Information (FMC:State)
- dcterms:description: Data provided by various authoring tools such as System Engineering Modeling Tools, Mechanical or Electrical CAD Tools. All are partial information concerning the same product and shall be analyzed and used in a common context.
- dcterms:type: ArchiMate:BusinessObject

## Read File (FMC:Actor)
- dcterms:description: Read a file from local disk or from URL.
- dcterms:type: ArchiMate:ApplicationFunction

## reqif-to-cas.xsl (FMC:State)
- dcterms:description: A XSL stylesheet to extract relevant data from a ReqIF file. It is assumed that the source file to transform complies with the OMG Standard [Requirements Interchange Format (ReqIF)](https://www.omg.org/reqif/) and with the Prostep ivip [Implementation Guideline ReqIF](https://www.prostep.org/shop/detail?ai%5Baction%5D=detail&ai%5Bcontroller%5D=Catalog&ai%5Bd_name%5D=reqif_ig_v1-7&ai%5Bd_pos%5D=).

  The fact that the ReqIF Implementation Guideline proposes certain attribute names as a convention, but no names for the entities (called OBJECT-TYPES) themselves, is a challenge for semantic interoperability. However, daily practice has adopted a number of entity names which can be included in the [[any-to-cas.mvf]] to find appropriate ontology classes. It is advised to design the XSL stylesheet for ReqIF in a way that the LONG-NAME of all OBJECT-TYPES is taken as entity class name and to leave all mapping with ontology terms to a subsequent process step, see [[Assign Ontology Class]].
- dcterms:type: ArchiMate:DataObject

## Single-User App (SpecIF:Collection)
- dcterms:description: A stand-alone browser app. Data persistence is achieved by exporting a comprehensive file in JSON-LD and re-importing it in the next session. In addition, a browser database can be used.
- dcterms:type: ArchiMate:Grouping

## Sink Data (FMC:State)
- dcterms:description: The most general term for data produced by the CASCaRA App for further processing.
- dcterms:type: ArchiMate:DataObject

## Source Data (FMC:State)
- dcterms:description: The most general term for data ingested by the CASCaRA App from previous processing steps.
- dcterms:type: ArchiMate:DataObject

## SPARQL Engine (FMC:Actor)
- dcterms:description: An engine performing a transformation using the SPARQL Protocol and RDF Query Language.
- dcterms:type: ArchiMate:ApplicationService

## Test Data [Original] (FMC:State)
- dcterms:description: Test data in a format provided by an [[Original Authoring System]].
- dcterms:type: ArchiMate:DataObject

## Test Data [RDF] (FMC:State)
- dcterms:description: Test data in RDF/Turtle format to allow further processing and reasoning with tools of the RDF ecosystem.
- dcterms:type: ArchiMate:DataObject

## Transform to Subgraph (SPARQL) (FMC:Actor)
- dcterms:description: Transform the input data with its original Turtle format to a CASCaRA compliant subgraph. SPARQL queries defined in [[any-to-cas.sparql]] are used.
- dcterms:type: ArchiMate:ApplicationFunction

## Transform to Subgraph (XSLT) (FMC:Actor)
- dcterms:description: Transform the input data with its original XML format (such as ReqIF) to a CASCaRA compliant subgraph. A stylesheet per input format such as [[reqif-to-cas.xsl]] is used. It is advised that the stylesheet is designed to keep the original terminology, so that the transformation is as generally applicable as possible and to assign CASCaRA Ontology classes in a subsequent process step.
- dcterms:type: ArchiMate:ApplicationFunction

## Transform XML to JSON (FMC:Actor)
- dcterms:description: XML data compliant with the CASCaRA metamodel is transformed to the equivalent CASCaRA JSON-LD format.
- dcterms:type: ArchiMate:ApplicationFunction

## Triple-Store (FMC:Actor)
- dcterms:description: A standard database for knowledge graphs, e.g. Apache Fuseki.
- dcterms:type: ArchiMate:ApplicationComponent

## UI Plugin (FMC:Actor)
- dcterms:description: User Interface, such as 
  - viewer, 
  - editor by forms or diagramming.

  The user-interface is class-driven, i.e. the details of the entity, relationship or organizer classes with their respective property classes determine the UI. For example, an editing form for a class with three property classes will have 3 fields expecting input according to its datatype and range. Or a graphical editor for a UML interaction diagram will present a tailored palette with drawing rules for interaction diagrams.
- dcterms:type: ArchiMate:ApplicationComponent

## Validation Plugin (FMC:Actor)
- dcterms:description: Validates a package or a collection of packages, with
  - schema checking
  - constraint/consistency checking.
- dcterms:type: ArchiMate:ApplicationComponent

## Weave Subgraph into Graph (FMC:Actor)
- dcterms:description: A subgraph transformed form input data is first mapped to the CASCaRA Ontology, checked by schema and constraints and then integrated in the common [[Graph]].
- dcterms:type: ArchiMate:BusinessFunction

## Web-Server (FMC:Actor)
- dcterms:description: A standard web-server used for publication and exchange of information.
- dcterms:type: ArchiMate:ApplicationComponent

## XSLT Engine (FMC:Actor)
- dcterms:description: An engine performing a transformation using the Extensible Stylesheet Language (XSL).
- dcterms:type: ArchiMate:ApplicationService

## Statements
- App SpecIF:shows CASCaRA App
- App SpecIF:shows Controller
- App SpecIF:shows KP Storage Adapter
- App SpecIF:shows FS Storage Adapter
- App SpecIF:shows Other Storage Adapter
- App SpecIF:shows Export Adapter
- App SpecIF:shows Import Adapter
- App SpecIF:shows Model Integration Plugin
- App SpecIF:shows UI Plugin
- App SpecIF:shows Validation Plugin
- App SpecIF:shows Ontology Plugin
- App SpecIF:shows Knowledge Platform
- App SpecIF:shows File System
- App SpecIF:shows Knowledge File
- App SpecIF:shows Web-Server
- App SpecIF:shows Source Data
- App SpecIF:shows Sink Data
- Server SpecIF:shows CASCaRA Server
- Server SpecIF:shows CASCaRA API
- Server SpecIF:shows Common Lib
- Server SpecIF:shows Cache
- Server SpecIF:shows API4KP
- Server SpecIF:shows Document-DB Storage Adapter
- Server SpecIF:shows Graph-DB Storage Adapter
- Server SpecIF:shows MCP API
- Import Processing SpecIF:shows CASCaRA Graph
- Import Processing SpecIF:shows Graph
- Import Processing SpecIF:shows Partial Information
- Import Processing SpecIF:shows input.cas.ttl
- Import Processing SpecIF:shows input.cas.jsonld
- Import Processing SpecIF:shows Create CASCaRA Subgraph
- Import Processing SpecIF:shows Read File
- Import Processing SpecIF:shows Check CASCaRA JSON-LD Schema
- Import Processing SpecIF:shows Check CASCaRA XML Schema
- Import Processing SpecIF:shows input.reqif
- Import Processing SpecIF:shows Source Data
- Import Processing SpecIF:shows XSLT Engine
- Import Processing SpecIF:shows reqif-to-cas.xsl
- Import Processing SpecIF:shows MVF Engine
- Import Processing SpecIF:shows any-to-cas.mvf
- Import Processing SpecIF:shows Weave Subgraph into Graph
- Import Processing SpecIF:shows Check CASCaRA JSON Schema
- Import Processing SpecIF:shows Check Package Constraints
- Import Processing SpecIF:shows Integrate Subgraph
- Import Processing SpecIF:shows Transform to Subgraph (XSLT)
- Import Processing SpecIF:shows Assign Ontology Class
- Import Processing SpecIF:shows SPARQL Engine
- Import Processing SpecIF:shows Transform to Subgraph (SPARQL)
- Import Processing SpecIF:shows input.cas.xml
- Import Processing SpecIF:shows Transform XML to JSON
- Import Processing SpecIF:shows Configuration Data
- Import Processing SpecIF:shows any-to-cas.sparql
- Import Processing SpecIF:shows JSON Schema Engine
- Import Processing SpecIF:shows itemType.json
- Validation Process SpecIF:shows CASCaRA App
- Validation Process SpecIF:shows Import Adapter
- Validation Process SpecIF:shows Export Adapter
- Validation Process SpecIF:shows Validation Plugin
- Validation Process SpecIF:shows UI Plugin
- Validation Process SpecIF:shows Triple-Store
- Validation Process SpecIF:shows File System
- Validation Process SpecIF:shows Sink Data
- Validation Process SpecIF:shows Test Data [RDF]
- Validation Process SpecIF:shows Source Data
- Validation Process SpecIF:shows Test Data [Original]
- Validation Process SpecIF:shows Original Authoring System
- Validation Process SpecIF:shows CASCaRA Validation Process
- Validation Process SpecIF:shows Create Test-Data
- Validation Process SpecIF:shows Apply Competency Question
- Validation Process SpecIF:shows Check Schema, Consistency and Completeness
- Validation Process SpecIF:shows Business Use-Case
- Configuration Options SpecIF:shows Single-User App
- Configuration Options SpecIF:shows data.cas.jsonld
- Configuration Options SpecIF:shows CASCaRA App
- Configuration Options SpecIF:shows Import Adapter
- Configuration Options SpecIF:shows Export Adapter
- Configuration Options SpecIF:shows Common Lib
- Configuration Options SpecIF:shows 2-Layer Client-Server
- Configuration Options SpecIF:shows CASCaRA Server Adapter
- Configuration Options SpecIF:shows CASCaRA Server
- Configuration Options SpecIF:shows Graph Database
- Configuration Options SpecIF:shows CASCaRA API
- Configuration Options SpecIF:shows 3-Layer Client-Server
- Configuration Options SpecIF:shows Graph-DB Server
- Configuration Options SpecIF:shows Graph-DB Storage Adapter
- Knowledge Platform SpecIF:serves KP Storage Adapter
- CASCaRA App SpecIF:contains Controller
- CASCaRA App SpecIF:contains KP Storage Adapter
- File System SpecIF:accesses Knowledge File
- File System SpecIF:serves FS Storage Adapter
- CASCaRA App SpecIF:contains FS Storage Adapter
- CASCaRA App SpecIF:contains Other Storage Adapter
- CASCaRA App SpecIF:contains Export Adapter
- CASCaRA App SpecIF:contains Import Adapter
- CASCaRA App SpecIF:contains Model Integration Plugin
- FS Storage Adapter SpecIF:serves Controller
- KP Storage Adapter SpecIF:serves Controller
- Other Storage Adapter SpecIF:serves Controller
- CASCaRA App SpecIF:contains UI Plugin
- CASCaRA App SpecIF:contains Validation Plugin
- Validation Plugin SpecIF:serves Controller
- Import Adapter SpecIF:serves Controller
- Model Integration Plugin SpecIF:serves Controller
- UI Plugin SpecIF:serves Controller
- Export Adapter SpecIF:serves Controller
- File System SpecIF:writes Source Data
- Web-Server SpecIF:writes Source Data
- Web-Server SpecIF:serves Import Adapter
- File System SpecIF:serves Import Adapter
- Web-Server SpecIF:writes Sink Data
- File System SpecIF:writes Sink Data
- Web-Server SpecIF:serves Export Adapter
- File System SpecIF:serves Export Adapter
- File System SpecIF:serves CASCaRA App
- File System SpecIF:serves Triple-Store
- File System SpecIF:writes Test Data [RDF]
- Test Data [RDF] uml:isSpecializationOf Sink Data
- File System SpecIF:writes Test Data [Original]
- Test Data [Original] uml:isSpecializationOf Source Data
- File System SpecIF:serves Original Authoring System
- Original Authoring System SpecIF:contains Create Test-Data
- CASCaRA Validation Process SpecIF:contains Create Test-Data
- CASCaRA Validation Process SpecIF:contains Apply Competency Question
- Triple-Store SpecIF:contains Apply Competency Question
- Create Test-Data SpecIF:reads Business Use-Case
- Apply Competency Question SpecIF:reads Business Use-Case
- CASCaRA Validation Process SpecIF:contains Check Schema, Consistency and Completeness
- CASCaRA App SpecIF:contains Check Schema, Consistency and Completeness
- Create Test-Data SpecIF:precedes Check Schema, Consistency and Completeness
- Check Schema, Consistency and Completeness SpecIF:precedes Apply Competency Question
- Check Schema, Consistency and Completeness SpecIF:reads Business Use-Case
- CASCaRA App SpecIF:contains Ontology Plugin
- Ontology Plugin SpecIF:serves UI Plugin
- CASCaRA App SpecIF:serves Ontology Plugin
- Ontology Plugin SpecIF:serves Validation Plugin
- Ontology Plugin SpecIF:serves Model Integration Plugin
- Ontology Plugin SpecIF:serves Import Adapter
- Ontology Plugin SpecIF:serves Export Adapter
- Original Authoring System SpecIF:writes Test Data [Original]
- Import Adapter SpecIF:reads Test Data [Original]
- Export Adapter SpecIF:writes Test Data [RDF]
- Triple-Store SpecIF:reads Test Data [RDF]
- CASCaRA App SpecIF:reads Source Data
- CASCaRA App SpecIF:writes Sink Data
- input.reqif uml:isSpecializationOf Source Data
- Read File SpecIF:reads input.reqif
- XSLT Engine SpecIF:serves Transform to Subgraph (XSLT)
- Transform to Subgraph (XSLT) SpecIF:reads reqif-to-cas.xsl
- Read File SpecIF:precedes Transform to Subgraph (XSLT)
- MVF Engine SpecIF:serves Assign Ontology Class
- MVF Engine SpecIF:reads any-to-cas.mvf
- Transform to Subgraph (XSLT) SpecIF:precedes Transform XML to JSON
- Assign Ontology Class SpecIF:precedes Check CASCaRA JSON Schema
- Check Package Constraints SpecIF:precedes Integrate Subgraph
- Integrate Subgraph SpecIF:accesses Graph
- input.cas.jsonld uml:isSpecializationOf Source Data
- Read File SpecIF:reads input.cas.jsonld
- Read File SpecIF:precedes Check CASCaRA JSON-LD Schema
- Create CASCaRA Subgraph SpecIF:precedes Weave Subgraph into Graph
- Weave Subgraph into Graph SpecIF:writes CASCaRA Graph
- Graph SpecIF:contains CASCaRA Graph
- Transform to Subgraph (XSLT) SpecIF:contains Create CASCaRA Subgraph
- Read File SpecIF:contains Create CASCaRA Subgraph
- Create CASCaRA Subgraph SpecIF:reads Partial Information
- Read File SpecIF:reads input.cas.ttl
- SPARQL Engine SpecIF:serves Transform to Subgraph (SPARQL)
- Read File SpecIF:precedes Transform to Subgraph (SPARQL)
- Transform to Subgraph (SPARQL) SpecIF:precedes Assign Ontology Class
- input.cas.ttl uml:isSpecializationOf Source Data
- Read File SpecIF:reads input.cas.xml
- Transform XML to JSON SpecIF:precedes Assign Ontology Class
- Read File SpecIF:precedes Check CASCaRA XML Schema
- input.cas.xml uml:isSpecializationOf Source Data
- input.cas.xml SpecIF:contains Partial Information
- input.cas.jsonld SpecIF:contains Partial Information
- input.reqif SpecIF:contains Partial Information
- input.cas.ttl SpecIF:contains Partial Information
- Transform XML to JSON SpecIF:contains Create CASCaRA Subgraph
- Transform to Subgraph (SPARQL) SpecIF:contains Create CASCaRA Subgraph
- Assign Ontology Class SpecIF:contains Weave Subgraph into Graph
- Check CASCaRA JSON Schema SpecIF:contains Weave Subgraph into Graph
- Integrate Subgraph SpecIF:contains Weave Subgraph into Graph
- Check CASCaRA JSON Schema SpecIF:precedes Check Package Constraints
- Check CASCaRA JSON-LD Schema SpecIF:precedes Assign Ontology Class
- SPARQL Engine SpecIF:reads any-to-cas.sparql
- any-to-cas.sparql uml:isSpecializationOf Configuration Data
- any-to-cas.mvf uml:isSpecializationOf Configuration Data
- reqif-to-cas.xsl uml:isSpecializationOf Configuration Data
- Check CASCaRA XML Schema SpecIF:contains Create CASCaRA Subgraph
- Check CASCaRA XML Schema SpecIF:precedes Transform XML to JSON
- JSON Schema Engine SpecIF:serves Check CASCaRA JSON Schema
- JSON Schema Engine SpecIF:serves Check CASCaRA JSON-LD Schema
- itemType.json uml:isSpecializationOf Configuration Data
- JSON Schema Engine SpecIF:reads itemType.json
- CASCaRA Server SpecIF:contains CASCaRA API
- CASCaRA Server SpecIF:contains Common Lib
- CASCaRA Server SpecIF:contains API4KP
- CASCaRA Server SpecIF:contains Document-DB Storage Adapter
- Document-DB Storage Adapter SpecIF:serves Common Lib
- Common Lib SpecIF:serves API4KP
- Common Lib SpecIF:serves CASCaRA API
- CASCaRA Server SpecIF:contains Graph-DB Storage Adapter
- Graph-DB Storage Adapter SpecIF:serves Common Lib
- CASCaRA Server SpecIF:contains MCP API
- Common Lib SpecIF:serves MCP API
- Common Lib SpecIF:accesses Cache
- Import Adapter SpecIF:reads data.cas.jsonld
- Export Adapter SpecIF:writes data.cas.jsonld
- CASCaRA App SpecIF:contains CASCaRA Server Adapter
- CASCaRA API SpecIF:serves CASCaRA Server Adapter
- CASCaRA Server SpecIF:writes Graph Database
- 3-Layer Client-Server SpecIF:contains CASCaRA Server
- 3-Layer Client-Server SpecIF:contains CASCaRA App
- 3-Layer Client-Server SpecIF:contains Graph-DB Server
- Graph-DB Server SpecIF:serves Graph-DB Storage Adapter
- 2-Layer Client-Server SpecIF:contains CASCaRA App
- 2-Layer Client-Server SpecIF:contains CASCaRA Server
- Single-User App SpecIF:contains CASCaRA App
- CASCaRA App SpecIF:contains Common Lib
- CASCaRA Server Adapter SpecIF:serves Common Lib
- Import Adapter SpecIF:serves Common Lib
- Export Adapter SpecIF:serves Common Lib
- File System SpecIF:contains Knowledge File
- Web-Server SpecIF:contains Source Data
- File System SpecIF:contains Source Data
- Web-Server SpecIF:contains Sink Data
- File System SpecIF:contains Sink Data
- Common Lib SpecIF:contains Cache
- Create CASCaRA Subgraph SpecIF:contains Check CASCaRA JSON-LD Schema
- Weave Subgraph into Graph SpecIF:contains Check Package Constraints
- File System SpecIF:contains Test Data [RDF]
- File System SpecIF:contains Test Data [Original]
- Single-User App SpecIF:contains data.cas.jsonld
- CASCaRA Server SpecIF:contains Graph Database
