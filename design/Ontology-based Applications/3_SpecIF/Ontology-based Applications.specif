# Ontology-based Applications
- Rights: Creative Commons 4.0 CC BY-SA, https://creativecommons.org/licenses/by-sa/4.0/

## Ontology-based Applications (SpecIF:Heading)
- dcterms:type: SpecIF:Outline

## SpecIF:Views (SpecIF:Heading)

## From Ontology Definition to Data Management and Data Use (cas:View)
- dcterms:description: A process for ontology-based applications with three steps is shown:
  1. The application ontology is edited using the CASCaRA metamodel classes for ontologies. For example the terms (concepts) for *library*, *book* and *author* plus their relationships *owned-by* and *written-by* are defined.
  2. The application data is edited using the classes for application as generated from the application ontology. For example, libraries, books and authors are defined with their relationships.
  3. The application data is stored in a graph database, a so-called Triple-Store. For example, the users can query the data to list all libraries owning a given book or to list all authors found in a given library. The latter is a *graph search* which is particularly performant when graph databases are used.

  The process is shown using the ArchiMate notation. Business-related elements are yellow and IT-application-related elements are blue. The BPMN notation would show a lane per role *Ontologist*, *Data Steward* and *User* at the top and the business functions shown underneath as process steps within.

  All data conforms to the CASCaRA metamodel, either in JSON-LD or Turtle format.

  If you like, have a look at the demonstration:

  | Step | Libraries (Example ) | Develop your own example |
  | --- | --- | --- |
  | 1 | Open an [Editor](https://specif.de/apps/edit#import="https://cascara.gfse.org/examples/libraries/data/Library-Ontology%20(Example).specif") with loaded classes for building an ontology and some terms. You can add terms of the library domain. | Open an [Editor](https://specif.de/apps/edit#import="https://cascara.gfse.org/examples/data/Classes-for-Ontology.specif") with loaded classes for building an ontology. You can add terms of your application domain. |
  | 2 | Inspect the [Library Ontology as HTML](https://cascara.gfse.org/examples/libraries/Library-Ontology%20(Example).html).<br/>Download the [Classes for Libraries](https://cascara.gfse.org/examples/libraries/data/Classes-for-Libraries.specif) (as generated from the Library Ontology) to load in the editor in the next step. | Export SpecIF Class Definitions (third option) to load in the next step. |
  | 3 | Open an [Editor](https://specif.de/apps/edit#import="https://cascara.gfse.org/examples/libraries/data/Libraries%20(Example).specif") with loaded classes for managing libraries and some instances. You can add data according to the library ontology defined above. | Open an [Editor](https://specif.de/apps/edit) ready to load classes for managing application data exported above. You can add data according to your application ontology. |
  | 4 | Inspect the [Library Data as HTML](https://cascara.gfse.org/examples/libraries/Libraries%20(Example).html)<br/>Download the [Library Data as Turtle](https://cascara.gfse.org/examples/libraries/data/Libraries%20(Example).ttl) to load in the next step. | Export your application data  (Turtle) to load in the next step. |
  | 5 | Load the library data to your favorite graph database, e.g. [Apache Fuseki](https://jena.apache.org/documentation/fuseki2/). | Load your application data to your favorite graph database, e.g. [Apache Fuseki](https://jena.apache.org/documentation/fuseki2/). |

  Please note: The demonstration uses the SpecIF tools until the CASCaRA tools are available. If you like the approach, support our implementation team validating the [CASCaRA standard in preparation](https://cascara.gfse.org)!
- cas:Diagram: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
- dcterms:type: ArchiMate:Viewpoint
- cas:Notation: Application Usage

## Business (SpecIF:Heading)
- dcterms:type: SpecIF:Heading

## Data Management (FMC:Actor)
- dcterms:description: Given a software application that manages the assets (inventory) of a library, the data of the books, their authors and the owning libraries is collected and entered.
- dcterms:type: ArchiMate:BusinessProcess

## Data Steward (FMC:Actor)
- dcterms:description: Responsible for defining the application data using the classes of the application ontology. In a different domain the Data Steward may be a Systems Engineer using a dedicated authoring tool.
- dcterms:type: ArchiMate:BusinessRole

## Data Use (FMC:Actor)
- dcterms:description: Given a software application that has a database of books, their authors and owning libraries, a book catalog with search capabilities may be displayed.
- dcterms:type: ArchiMate:BusinessProcess

## Edit Application Data (FMC:Actor)
- dcterms:description: Edit (create and maintain) the application data.
- dcterms:type: ArchiMate:BusinessFunction

## Edit Application Ontology (FMC:Actor)
- dcterms:description: Edit (create and maintain) the application ontology.
- dcterms:type: ArchiMate:BusinessFunction

## Ontologist (FMC:Actor)
- dcterms:description: Responsible for defining the application ontology, i.e. the concepts and terms with their relationships within a given application domain, such as library management in this example or systems engineering in another.
- dcterms:type: ArchiMate:BusinessRole

## Ontology Definition (FMC:Actor)
- dcterms:description: In ontology-driven application development, the first step is to define the entities and their relationships of the application domain, called the application ontology.

  For example, the ontology of a simple library asset management system (or inventory management system of a library), would include the entities are book, author plus library and the relationships are written-by plus owned-by, where the former is restricted to book-author relationships and the latter is restricted to book-library relationships.
- dcterms:type: ArchiMate:BusinessProcess

## Use Application Data (FMC:Actor)
- dcterms:description: Use (query and check) the application data.
- dcterms:type: ArchiMate:BusinessFunction

## User (FMC:Actor)
- dcterms:description: Responsible for using (querying and even checking) the application data.
- dcterms:type: ArchiMate:BusinessRole

## Application (SpecIF:Heading)
- dcterms:type: SpecIF:Heading

## Application Data [JSON-LD] (FMC:State)
- dcterms:description: Classes and instances (individuals) representing the application data. The data structure (pattern) conforms with the [CASCaRA Metamodel](https://product-information-graph.org/doc/metamodel/latest/).
- dcterms:type: ArchiMate:DataObject

## Application Data [RDF] (FMC:State)
- dcterms:description: Classes and instances (individuals) representing the application ontology. The data structure (pattern) conforms with the [CASCaRA Metamodel](https://product-information-graph.org/doc/metamodel/latest/), so that standard queries can be used.
- dcterms:type: ArchiMate:DataObject

## Application Data [Turtle] (FMC:State)
- dcterms:description: Classes and instances (individuals) representing the application data. The data structure (pattern) conforms with the [CASCaRA Metamodel](https://product-information-graph.org/doc/metamodel/latest/).
- dcterms:type: ArchiMate:DataObject

## Application Ontology [JSON-LD] (FMC:State)
- dcterms:description: Classes and instances (individuals) representing the application ontology. The data structure (pattern) conforms with the [CASCaRA Metamodel](https://product-information-graph.org/doc/metamodel/latest/).
- dcterms:type: ArchiMate:DataObject

## CASCaRA App (FMC:Actor)
- dcterms:description: A web application for creating, reading, updating and deleting data elements per class. The app is configured by the classes loaded at initialization time. The classes govern the choice and the dialog layout for modifying the data. Thus, the same software is used for more or less complex applications. In this case, the CASCaRA App is used both for defining the application ontology and the application data.
- dcterms:type: ArchiMate:ApplicationComponent

## Classes for Application [JSON-LD] (FMC:State)
- dcterms:description: A set of classes allowing to manage application data. The data structure (pattern) conforms with the [CASCaRA Metamodel](https://product-information-graph.org/doc/metamodel/latest/).
- dcterms:type: ArchiMate:DataObject

## Classes for Ontology [JSON-LD] (FMC:State)
- dcterms:description: A set of classes allowing to define an ontology. The data structure (pattern) conforms with the [CASCaRA Metamodel](https://product-information-graph.org/doc/metamodel/latest/).
- dcterms:type: ArchiMate:DataObject

## Triple-Store (FMC:Actor)
- dcterms:description: A standard database for knowledge graphs, e.g. Apache Fuseki.
- dcterms:type: ArchiMate:ApplicationComponent

## Model Elements (Glossary) (SpecIF:Heading)
- dcterms:type: SpecIF:Glossary

## Statements
- From Ontology Definition to Data Management and Data Use SpecIF:shows Data Use
- From Ontology Definition to Data Management and Data Use SpecIF:shows Data Management
- From Ontology Definition to Data Management and Data Use SpecIF:shows Ontology Definition
- From Ontology Definition to Data Management and Data Use SpecIF:shows CASCaRA App
- From Ontology Definition to Data Management and Data Use SpecIF:shows Classes for Ontology [JSON-LD]
- From Ontology Definition to Data Management and Data Use SpecIF:shows Classes for Application [JSON-LD]
- From Ontology Definition to Data Management and Data Use SpecIF:shows Application Ontology [JSON-LD]
- From Ontology Definition to Data Management and Data Use SpecIF:shows Application Data [JSON-LD]
- From Ontology Definition to Data Management and Data Use SpecIF:shows Application Data [Turtle]
- From Ontology Definition to Data Management and Data Use SpecIF:shows Triple-Store
- From Ontology Definition to Data Management and Data Use SpecIF:shows Application Data [RDF]
- From Ontology Definition to Data Management and Data Use SpecIF:shows Ontologist
- From Ontology Definition to Data Management and Data Use SpecIF:shows Edit Application Ontology
- From Ontology Definition to Data Management and Data Use SpecIF:shows Edit Application Data
- From Ontology Definition to Data Management and Data Use SpecIF:shows Data Steward
- From Ontology Definition to Data Management and Data Use SpecIF:shows Use Application Data
- From Ontology Definition to Data Management and Data Use SpecIF:shows User
- CASCaRA App SpecIF:reads Classes for Ontology [JSON-LD]
- CASCaRA App SpecIF:writes Classes for Application [JSON-LD]
- CASCaRA App SpecIF:reads Classes for Application [JSON-LD]
- CASCaRA App SpecIF:accesses Application Ontology [JSON-LD]
- CASCaRA App SpecIF:accesses Application Data [JSON-LD]
- CASCaRA App SpecIF:writes Application Data [Turtle]
- Triple-Store SpecIF:reads Application Data [Turtle]
- Triple-Store SpecIF:accesses Application Data [RDF]
- CASCaRA App SpecIF:serves Edit Application Ontology
- Ontologist SpecIF:contains Edit Application Ontology
- CASCaRA App SpecIF:serves Edit Application Data
- Data Steward SpecIF:contains Edit Application Data
- Triple-Store SpecIF:serves Use Application Data
- User SpecIF:contains Use Application Data
- Edit Application Ontology SpecIF:precedes Edit Application Data
- Edit Application Data SpecIF:precedes Use Application Data
- Ontologist SpecIF:contains Ontology Definition
- Ontology Definition SpecIF:contains Edit Application Ontology
- Data Steward SpecIF:contains Data Management
- Data Management SpecIF:contains Edit Application Data
- User SpecIF:contains Data Use
- Data Use SpecIF:contains Use Application Data
- Ontology Definition SpecIF:precedes Data Management
- Data Management SpecIF:precedes Data Use
