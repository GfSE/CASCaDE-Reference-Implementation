# Specification: 3000 Requirements
- ReqIF.Name: 3000 Requirements

## R1: Legal requirements (Klasse)

### R2: Legal safety requirements manufacturing (Klasse)

### R3: Legal safety requirement testing (Klasse)

### R4: Legal ergonomy requierments manufacturing (Klasse)

## 2: Technical requirements (Requirement)

### 2.1: Structure (Requirement)

#### 2.1.1: Head (Requirement)
The Mars Rover shall have a head

##### 2.1.1.1: Head Position (Requirement)
The Head of the Mars Rover shall be higher mounted than body, suspension and traction unit.

##### 2.1.1.2: Head Function (Functional Requirement)
The Head of the Mars Rover shall carry sensors and a LED Display.

#### 2.1.2: Body (Requirement)
The Mars Rover shall have a body

#### 2.1.3: Suspension (Functional Requirement)
The Mars Rover shall have a suspension suspending the traction unit

#### 2.1.4: Traction Unit (Functional Requirement)
The Mars Rover shall have a traction unit providing traction to the ground

### 2.2: Power Supply (Requirement)
The Mars Rover shall have a power supply.

#### 2.2.1: External Power Supply (Requirement)
The Mars Rover shall be operable with internal power supply only.

#### 2.2.2: Internal Power Supply (Requirement)
The Mars Rover shall have a power supply fulfilling all of the following conditions:
* it contains an energy storage system
* it contains an energy management system
* it contains a power distribution system

##### 2.2.2.1: Energy Storage (Functional Requirement)
The Mars Rover shall have means to re-charde its energy storage system.

##### 2.2.2.2: Available Power (Requirement)
The Mars Rover shall be operable for 4h under all of the following conditions:
* The energy storage is fully loaded at the beginning
* The operation requires less than or equal to 60% of the max energy in peak load
* the environmental conditions are mission normal

#### 2.2.3: Energy Re-Charging (Functional Requirement)
The Mars Rover shall re-charge the energy storage from 10% to 80% in 4h under the following conditions:
* re-charging at mission normal conditions
* no energy consumption of the Mars Rover since the re-charging period
- DeriveReqt -> 2.2.4
- DeriveReqt -> 2.2.5
- DeriveReqt -> 2.3.5

#### 2.2.5: Electrical Values (Requirement)
The Mars Rover shall use 12 V DC voltage

##### 2.2.5.1: Motor Voltage (Requirement)
The Mars Rover shall have one main drive motor for each traction device fulfilling the following conditions:
* using 12 V voltage
* using not more than 30 A current
- Trace -> 2.3.4
- Trace -> 2.2.5

##### 2.2.5.2: Encoder Voltage (Requirement)
The Mars Rover shall have an encoder powered by 5 V voltage.

#### 2.2.4: Energy Management (Functional Requirement)
The Mars Rover shall have an energy management fullfilling all of the following conditions:
* distributing the energy to all systems
* prioritizing the energy available for the different systems
* limiting energy to individual systems to prioritize individual systems
* managing energy that the Mars Rover can recharge by itself in a time period of less than 24 hours

### 2.3: Motion (Requirement)
The Mars Rover shall be able to move by itself.

#### 2.3.2: Motion over Obstacles (Functional Requirement)
The Mars Rover shall be able to move by itself over obstacles which fullfill one of the following condition:
* the obstacle is max. 20 cm high
* the slope angle uphil is max. 30 degree
* the slope angle downhil is max. 30 degree
* the roll angle of the Mars Rover since moving over the obstacle never exceeds an angle of 30 degree

##### 2.3.2.1: Deformation of the bogie (Requirement)
The bogie of the suspension system shall not bend more than 5% since all motion events.
- Refine -> 2.3.2

##### 2.3.2.2: Plastic deformation of the bogie (Requirement)
The bogie of the suspension system shall not deform plastically for bending less than or equal to 7%.

#### 2.3.4: Motion Ground Contact (Functional Requirement)
The Mars Rover shall produce a ground pressure of max. 20 kPa.
- Trace -> 2.3

#### 2.3.1: Max Motion Speed (Functional Requirement)
The Mars Rover shall be able to move by itself with a max. speed of 7 m/s.

#### 2.3.3: Motion over slopes (Functional Requirement)
The Mars Rover shall be able to move on slopes which fullfill the following condition:
* slope angle uphill max. 20 degree
* slope angle downhill max. 30 degree
* slope angle sidehill max 15 degree

#### 2.3.5: Electric Motion Drive (Requirement)
The Mars Rover shall have one left and one right traction device both driven by one electrical motor each.

#### 2.3.8: Motion Distance (Requirement)
The Mars Rover shall be able to move at least 100m per day on all slopes where it is able to move on.
- Trace -> 2.3.1

#### 2.3.7: Min Motion Speed (Requirement)
The Mars Rover shall be able to move by itself with a min. speed of 1 m/min
- Trace -> 2.3.1

#### 2.3.6: Start Driving (Functional Requirement)
The Mars Rover shall start driving by itself on all slopes where it is able to move on.

#### 2.3.9: Stopping (Functional Requirement)
The Mars Rover shall be able to stop moving by itself down to 0 m/s speed.

#### 2.3.10: Hill Holding (Functional Requirement)
The Mars Rover shall maintain 0 m/s motion on all slopes it is able to move on.

#### 2.3.11: Steering (Functional Requirement)
The Mars Rover shall be able to change driving direction to the left and to the right.

#### 2.3.12: Diving Direction (Functional Requirement)
The Mars Rover shall be able to drive forwards and backwards.

#### 2.3.13: Navigate (Requirement)
The Mars Rover shall be able to calculate a route between its actual position and a target position

##### 2.3.13.1: Detecting Obstacles (Functional Requirement)
The Mars Rover shall be able to identify obstacles by itself

##### 2.3.13.2: Map Data (Functional Requirement)
The Mars Rover shall have map data stored enabling it to calculate a route between its actual position and a target position

##### 2.3.13.3: Preventing Obstacles (Functional Requirement)
The Mars Rover shall prevent driving over obstacles if all of the following conditions are true:
* the obstacle exceeds the measures of an acceptable obstacle as required in 1.1.3.2
* a rout is available around the obstacle or rearwards to a position capable to reach the target without crossing the obstacle.

### 2.4: Remote Control (Functional Requirement)
The Mars Rover shall be controllable remote.

#### 2.4.2: Remote Steering (Functional Requirement)
The Mars Rover steering direction shall be controllable remote.
- DeriveReqt -> 2.3.11

#### 2.4.1: Remote Speed Control (Functional Requirement)
The Mars Rover speed shall be controllable remote.

#### 2.4.3: Remote Control Priority (Usability Requirement)
The Mars Rover remote control shall be able to overrule the auto navigation function.

### 2.5: Optical Feedback (Functional Requirement)
The Mars Rover shall provide optical information if it is operable or not.

#### 2.5.1: LED (Requirement)
The Mars Rover shall have a LED for optical information if it is operable or not.
- DeriveReqt -> 2.1.1

### 2.6: Max Mass (Requirement)
The Mars Rover shall have a total mass of not more than 12 kg

#### 2.6.1: Mars Rover Mass (Usability Requirement)
The Mars Rover shall have a total mass of not more than 10 kg

#### 2.6.2: Payload (Requirement)
The Mars Rover shall have a payload of 2 kg.

### 2.7: Mars Rover Capabilities (Functional Requirement)
The Mars Rover shall be able to execute the following operations individually and not in combination:
* Moving on Mars surface
* Capturing optical information
* Capturing video information
* Capturing audio information
* Sampling of Probes of solid material of individual diameter not bigger than 20 mm
* Sampling of probes of fluid material in the range of ph-value 0 to 11
* Sampling of probes of gas of not more than 50 mm³ volume and pressure between 1 hPa up to 3.000 hPa
* Sampling of biological probes of not more than 50 mm³ volume and not more than 30 mm length in any direction

#### 2.7.1: Mars Rover Communication (Functional Requirement)
The Mars Rover shall be able to communicate sampled information to the Mars station.

#### 2.7.2: Information Storage (Functional Requirement)
The Mars Rover shall be capable to store information up to 2 TB

#### 2.7.3: Sample Storage (Functional Requirement)
The Mars Rover shall be able to store probes up to 48 h long.

#### 2.7.4: Unloading (Functional Requirement)
The Mars Rover shall be able to unload stored probes into the Mars Station.

### 2.9: Operating on Mars (Physical Requirement)
The Mars Rover shall be able to operate on the planet Mars.

#### 2.9.1: Operating Atmosphere (Physical Requirement)
The Mars Rover shall be able to operate in Mars atmosphere for at least 25 years.

#### 2.9.2: Mars Gravity (Physical Requirement)
The Mars Rover shall be able to operate under Mars gravity of 3.71 m/s².

#### 2.9.3: Mars Temperatures (Physical Requirement)
The Mars Rover shall be able to operate in a temperature range from -80°C up to 80°C

#### 2.9.4: Mars Radiation (Physical Requirement)
The Mars Rover shall be able to be fully operable under constant cosmic radiation of at least 250 mSv.

### 2.8: Landing on Mars (Physical Requirement)
The Mars Rover shall be able to land on planet Mars.

#### 2.8.1: Landing Temperatures (Physical Requirement)
The Mars Rover shall resist temperatures of not more than 100°C for not more than 7 minutes while staying full functional.

#### 2.8.2: Landing Deceleration (Physical Requirement)
The Mars Rover shall be able to withstand landing deceleration as listed below:
* Deceleration from 20.000 km/h at Mars atmosphere entry to 1.500 km/h in 4 minutes.
* Deceleration from 1.500 km/s to 25 m/s in 3 minutes

#### 2.8.3: Landing speed (Physical Requirement)
The Mars Rover shall be full operable after a landing on Mars with the following conditions beeing true:
* The vertical speed at ground contact is not higher than 1 m/s
* The horizontal speed at graund contact is not higher than 1 m/s

#### 2.8.4: Landing Orientation (Physical Requirement)
The Mars Rover shall land on Mars with the traction units first contacting the ground.
