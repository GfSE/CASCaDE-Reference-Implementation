# TC 1200 'Formated Content'

# Specification

## R1
- TC1200 AttributeDefinitionString: xhtml.p.type
- TC1200 AttributeDefinitionXHTML: text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R2
- TC1200 AttributeDefinitionString: xhtml.div.type
- TC1200 AttributeDefinitionXHTML: text before h1
  XhtmlH1Type
  text after h1 text before h2
  XhtmlH2Type
  text after h2 text before h3
  XhtmlH3Type
  text after h3 text before h4
  XhtmlH4Type
  text after h4 text before h5
  XhtmlH5Type
  text after h5 text before h6
  XhtmlH6Type
  text after h6 text before ul
  - XhtmlLiType
  text after ul text before ol
  1. XhtmlLiType
  text after ol text before dl
  XhtmlDtType
  XhtmlDdType
  text after dl text before p
  XhtmlPType
  text after p text before div
  XhtmlDivType
  text after div text before pre
  XhtmlPreType
  text after pre text before blockquote
  text after blockquote text before addressXhtmlAddressTypetext after address text before hr
  text after hr text before tabletext after table text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R3
- TC1200 AttributeDefinitionString: xhtml.br.type
- TC1200 AttributeDefinitionXHTML: XhtmlPType

## R4
- TC1200 AttributeDefinitionString: xhtml.span.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R5
- TC1200 AttributeDefinitionString: xhtml.em.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R6
- TC1200 AttributeDefinitionString: xhtml.strong.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R7
- TC1200 AttributeDefinitionString: xhtml.dfn.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R8
- TC1200 AttributeDefinitionString: xhtml.code.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R9
- TC1200 AttributeDefinitionString: xhtml.samp.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R10
- TC1200 AttributeDefinitionString: xhtml.kbd.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R11
- TC1200 AttributeDefinitionString: xhtml.var.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R12
- TC1200 AttributeDefinitionString: xhtml.cite.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R13
- TC1200 AttributeDefinitionString: xhtml.abbr.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R14
- TC1200 AttributeDefinitionString: xhtml.acronym.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R15
- TC1200 AttributeDefinitionString: xhtml.q.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R16
- TC1200 AttributeDefinitionString: xhtml.inl.pres.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R17
- TC1200 AttributeDefinitionString: xhtml.a.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before insXhtmlEditTypetext after ins text before delXhtmlEditTypetext after del

## R18
- TC1200 AttributeDefinitionString: xhtml.edit.type
- TC1200 AttributeDefinitionXHTML: XhtmlPType text before h1
  XhtmlH1Type
  text after h1 text before h2
  XhtmlH2Type
  text after h2 text before h3
  XhtmlH3Type
  text after h3 text before h4
  XhtmlH4Type
  text after h4 text before h5
  XhtmlH5Type
  text after h5 text before h6
  XhtmlH6Type
  text after h6 text before ul
  - XhtmlLiType
  text after ul text before ol
  1. XhtmlLiType
  text after ol text before dl
  XhtmlDtType
  XhtmlDdType
  text after dl text before p
  XhtmlPType
  text after p text before div
  XhtmlDivType
  text after div text before pre
  XhtmlPreType
  text after pre text before blockquote
  text after blockquote text before addressXhtmlAddressTypetext after address text before hr
  text after hr text before tabletext after table text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R19
- TC1200 AttributeDefinitionString: xhtml.h1.type
- TC1200 AttributeDefinitionXHTML: XhtmlDivType
  text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R20
- TC1200 AttributeDefinitionString: xhtml.h2.type
- TC1200 AttributeDefinitionXHTML: XhtmlDivType
  text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R21
- TC1200 AttributeDefinitionString: xhtml.h3.type
- TC1200 AttributeDefinitionXHTML: XhtmlDivType
  text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R22
- TC1200 AttributeDefinitionString: xhtml.h4.type
- TC1200 AttributeDefinitionXHTML: XhtmlDivType
  text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R23
- TC1200 AttributeDefinitionString: xhtml.h5.type
- TC1200 AttributeDefinitionXHTML: XhtmlDivType
  text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R24
- TC1200 AttributeDefinitionString: xhtml.h6.type
- TC1200 AttributeDefinitionXHTML: XhtmlDivType
  text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R25
- TC1200 AttributeDefinitionString: xhtml.ul.type
- TC1200 AttributeDefinitionXHTML: XhtmlDivType
  - XhtmlLiType

## R26
- TC1200 AttributeDefinitionString: xhtml.ol.type
- TC1200 AttributeDefinitionXHTML: XhtmlDivType
  1. XhtmlLiType

## R27
- TC1200 AttributeDefinitionString: xhtml.dl.type
- TC1200 AttributeDefinitionXHTML: XhtmlDivType
  XhtmlDtType
  XhtmlDdType

## R28
- TC1200 AttributeDefinitionString: xhtml.pre.type
- TC1200 AttributeDefinitionXHTML: XhtmlDivType
                      text before br
  text after br
                      text before spanXhtmlSpanTypetext after span
                      text before emXhtmlEmTypetext after em
                      text before strongXhtmlStrongTypetext after strong
                      text before dfnXhtmlDfnTypetext after dfn
                      text before codeXhtmlCodeTypetext after code
                      text before sampXhtmlSampTypetext after samp
                      text before kbdXhtmlKbdTypetext after kbd
                      text before varXhtmlVarTypetext after var
                      text before citeXhtmlCiteTypetext after cite
                      text before abbrXhtmlAbbrTypetext after abbr
                      text before acronymXhtmlAcronymTypetext after acronym
                      text before qXhtmlQTypetext after q
                      text before ttXhtmlInlPresTypetext after tt
                      text before iXhtmlInlPresTypetext after i
                      text before bXhtmlInlPresTypetext after b
                      text before aXhtmlATypetext after a
                      text before insXhtmlEditTypetext after ins
                      text before delXhtmlEditTypetext after del

## R29
- TC1200 AttributeDefinitionString: xhtml.blockquote.type
- TC1200 AttributeDefinitionXHTML: XhtmlDivType
  XhtmlH1Type
  XhtmlH2Type
  XhtmlH3Type
  XhtmlH4Type
  XhtmlH5Type
  XhtmlH6Type
  - XhtmlLiType
  1. XhtmlLiType
  XhtmlDtType
  XhtmlDdType
  XhtmlPType
  XhtmlDivType
  XhtmlPreType
  XhtmlAddressType
  XhtmlEditType XhtmlEditType

## R30
- TC1200 AttributeDefinitionString: xhtml.address.type
- TC1200 AttributeDefinitionXHTML: XhtmlDivType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R31
- TC1200 AttributeDefinitionString: xhtml.hr.type
- TC1200 AttributeDefinitionXHTML: XhtmlDivType

## R32
- TC1200 AttributeDefinitionString: xhtml.table.type
- TC1200 AttributeDefinitionXHTML: XhtmlDivType
  XhtmlCaptionType

## R33
- TC1200 AttributeDefinitionString: xhtml.li.type
- TC1200 AttributeDefinitionXHTML: XhtmlDivType
  - XhtmlLiType
  - text before h1
  XhtmlH1Type
  text after h1 text before h2
  XhtmlH2Type
  text after h2 text before h3
  XhtmlH3Type
  text after h3 text before h4
  XhtmlH4Type
  text after h4 text before h5
  XhtmlH5Type
  text after h5 text before h6
  XhtmlH6Type
  text after h6 text before ul
  - XhtmlLiType
  text after ul text before ol
  1. XhtmlLiType
  text after ol text before dl
  XhtmlDtType
  XhtmlDdType
  text after dl text before p
  XhtmlPType
  text after p text before div
  XhtmlDivType
  text after div text before pre
  XhtmlPreType
  text after pre text before blockquote
  text after blockquote text before addressXhtmlAddressTypetext after address text before hr
  text after hr text before tabletext after table text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R34
- TC1200 AttributeDefinitionString: xhtml.dt.type
- TC1200 AttributeDefinitionXHTML: XhtmlDivType
  XhtmlDtType
  XhtmlDdType
  text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del
  XhtmlDdType

## R35
- TC1200 AttributeDefinitionString: xhtml.dd.type
- TC1200 AttributeDefinitionXHTML: XhtmlDivType
  XhtmlDtType
  XhtmlDdType
  XhtmlDtType
  text before h1
  XhtmlH1Type
  text after h1 text before h2
  XhtmlH2Type
  text after h2 text before h3
  XhtmlH3Type
  text after h3 text before h4
  XhtmlH4Type
  text after h4 text before h5
  XhtmlH5Type
  text after h5 text before h6
  XhtmlH6Type
  text after h6 text before ul
  - XhtmlLiType
  text after ul text before ol
  1. XhtmlLiType
  text after ol text before dl
  XhtmlDtType
  XhtmlDdType
  text after dl text before p
  XhtmlPType
  text after p text before div
  XhtmlDivType
  text after div text before pre
  XhtmlPreType
  text after pre text before blockquote
  text after blockquote text before addressXhtmlAddressTypetext after address text before hr
  text after hr text before tabletext after table text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R36
- TC1200 AttributeDefinitionString: xhtml.caption.type
- TC1200 AttributeDefinitionXHTML: XhtmlDivType
  text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del

## R37
- TC1200 AttributeDefinitionString: xhtml.thead.type
- TC1200 AttributeDefinitionXHTML: XhtmlDivType

## R38
- TC1200 AttributeDefinitionString: xhtml.col.type
- TC1200 AttributeDefinitionXHTML: XhtmlDivType

## R39
- TC1200 AttributeDefinitionString: xhtml.colgroup.type
- TC1200 AttributeDefinitionXHTML: XhtmlDivType

## R40
- TC1200 AttributeDefinitionString: xhtml.tfoot.type
- TC1200 AttributeDefinitionXHTML: XhtmlDivType

## R41
- TC1200 AttributeDefinitionString: xhtml.tbody.type
- TC1200 AttributeDefinitionXHTML: XhtmlDivType

## R42
- TC1200 AttributeDefinitionString: xhtml.tr.type
- TC1200 AttributeDefinitionXHTML: XhtmlDivType
  | XhtmlThType | XhtmlTdType |
  | --- | --- |

## R43
- TC1200 AttributeDefinitionString: xhtml.td.type
- TC1200 AttributeDefinitionXHTML: XhtmlDivType
  |  | text before h1 XhtmlH1Type text after h1 text before h2 XhtmlH2Type text after h2 text before h3 XhtmlH3Type text after h3 text before h4 XhtmlH4Type text after h4 text before h5 XhtmlH5Type text after h5 text before h6 XhtmlH6Type text after h6 text before ul - XhtmlLiType text after ul text before ol 1. XhtmlLiType text after ol text before dl XhtmlDtType XhtmlDdType text after dl text before p XhtmlPType text after p text before div XhtmlDivType text after div text before pre XhtmlPreType text after pre text before blockquote text after blockquote text before addressXhtmlAddressTypetext after address text before hr text after hr text before tabletext after table text before br text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del |
  | --- | --- |

## R44
- TC1200 AttributeDefinitionString: xhtml.th.type
- TC1200 AttributeDefinitionXHTML: XhtmlDivType
  |  | text before h1 XhtmlH1Type text after h1 text before h2 XhtmlH2Type text after h2 text before h3 XhtmlH3Type text after h3 text before h4 XhtmlH4Type text after h4 text before h5 XhtmlH5Type text after h5 text before h6 XhtmlH6Type text after h6 text before ul - XhtmlLiType text after ul text before ol 1. XhtmlLiType text after ol text before dl XhtmlDtType XhtmlDdType text after dl text before p XhtmlPType text after p text before div XhtmlDivType text after div text before pre XhtmlPreType text after pre text before blockquote text after blockquote text before addressXhtmlAddressTypetext after address text before hr text after hr text before tabletext after table text before br text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before aXhtmlATypetext after a text before insXhtmlEditTypetext after ins text before delXhtmlEditTypetext after del |
  | --- | --- |
