# TC 1802 'HIS Exchange Process OEM -> SUP (2nd change)'

# Specification
- ReqIF.Name: Spec1

## R1: Obj-01
- A1: no change
- A2: no change
- E1: one

## R2: Obj-03
- A1: O3.A1 once
- A2: O3.A2 once
- E1: two

## R3: Obj-04
- A1: no change
- A2: no change
- E1: one

## R4: Obj-07
- A1: no change
- A2: no change
- E1: one

## R6: Obj-09
- A1: no change
- A2: no change
- E1: one

# Specification
- ReqIF.Name: Spec2

## R5: Obj-08
- A1: no change
- A2: no change
- E1: one
