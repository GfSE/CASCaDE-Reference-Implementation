# Project 'Related Terms'

# Specification: Project 'Related Terms'
- ReqIF.Name: Project 'Related Terms'

## R-1234: Lorry
Any of various conveyances running on rails, as for transporting material in a mine or factory. (Source: dictionary.com)
- SysML:isSpecialisationOf -> R-9876

## R-9876: Vehicle
Any means in or by which someone travels or something is carried or conveyed; a means of conveyance or transport. (Source: dictionary.com)
