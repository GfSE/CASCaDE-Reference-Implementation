## R1: A (Constraint Block)
- ELEMENT_SERVER_ID: 8eb894d6-4357-41ba-ae51-d5b145637f0e
- isEncapsulated: false

## R2: Battery_Constraint (Constraint Block)
- ELEMENT_SERVER_ID: 683d9a72-27f9-402b-a077-0eb14f3359a4
- isEncapsulated: false

## R3: Constraint_for_electrical_components_with_two_ports (Constraint Block)
- ELEMENT_SERVER_ID: c82ff8f4-b9b6-4d9f-b996-24a79127e26d
- isEncapsulated: false

## R4: Current_Divider (Constraint Block)
- ELEMENT_SERVER_ID: 220801dd-a70f-4ea3-a05a-53d0c9608ba6
- isEncapsulated: false

## R5: Drehmoment (Constraint Block)
- ELEMENT_SERVER_ID: d22ddf37-452e-4d27-8523-9724ca0b530f
- isEncapsulated: false

## R6: Gesamtwiderstand (Constraint Block)
- ELEMENT_SERVER_ID: 7cffd779-652f-497f-831b-d477bd555b5b
- isEncapsulated: false

## R7: Haftreibungszahl (Constraint Block)
- ELEMENT_SERVER_ID: 97234754-c799-49ff-b43d-b2f12617e130
- isEncapsulated: false

## R8: Mult_Calculate_Mass (Constraint Block)
- ELEMENT_SERVER_ID: 68942fc1-f098-4548-9918-acbf37c2d843
- isEncapsulated: false
- Association -> R146

## R9: Normalkraft (Constraint Block)
- ELEMENT_SERVER_ID: 324dfcff-f33d-49d3-9eea-a0be92242065
- isEncapsulated: false

## R10: Rollwiderstand (Constraint Block)
- ELEMENT_SERVER_ID: f7cc5278-3bc4-40e2-a965-1ca15e2b7bd1
- isEncapsulated: false

## R11: Rollwiderstandsbeiwert (Constraint Block)
- ELEMENT_SERVER_ID: b6be4cf0-7e84-44c0-ba16-9f8160d1b56b
- isEncapsulated: false

## R12: Signalverarbeitung (Constraint Block)
- ELEMENT_SERVER_ID: 904e6219-2fa5-460c-a65c-8ea993b6fcfb
- isEncapsulated: false

## R13: Sim_Motor (Constraint Block)
- ELEMENT_SERVER_ID: ad8187cb-a870-4a1f-8f77-b317f7a0011b
- isEncapsulated: false

## R14: Sim_Motor_Controller (Constraint Block)
- ELEMENT_SERVER_ID: e0aafc62-d05c-49fc-ae75-bd9fa709f788
- isEncapsulated: false

## R15: Sim_Serial_Splitter (Constraint Block)
- ELEMENT_SERVER_ID: 73ec0069-f3c5-43a3-bdc9-e6584ed8f2a5
- isEncapsulated: false

## R16: Sim_Voltage_regulator (Constraint Block)
- ELEMENT_SERVER_ID: 4d415fda-f280-4ed5-b32a-28bf9f6766a7
- isEncapsulated: false

## R17: Sim_Wirkende_Masse (Constraint Block)
- ELEMENT_SERVER_ID: 3aaa2854-d909-46cb-b10f-d4cc4f0ec584
- isEncapsulated: false

## R18: Steigungswiderstand (Constraint Block)
- ELEMENT_SERVER_ID: 115382cf-3085-4665-9aa3-ba553088c3f0
- isEncapsulated: false

## R19: Uebersetzung_RotationalSpeed (Constraint Block)
- ELEMENT_SERVER_ID: 8248532d-e140-431c-b3de-c2a4542167a9
- isEncapsulated: false

## R20: Uebersetzung_Torque (Constraint Block)
- ELEMENT_SERVER_ID: 87159941-42a9-43c1-a982-cfc3e88092c6
- isEncapsulated: false

## R21: Voltage_Regulator_Constraint (Constraint Block)
- ELEMENT_SERVER_ID: c30ea2ae-d25d-4c00-88f9-29ee8852a3be
- isEncapsulated: false

## R22: max_Haftreibungskraft (Constraint Block)
- ELEMENT_SERVER_ID: 050ae8bc-04fd-44d1-aef9-95c95b268080
- isEncapsulated: false

## R23: Notation eines Blockes (Block)
- ELEMENT_SERVER_ID: a4c9b20f-81de-43fb-a35e-a736bf3d0a3b
- isEncapsulated: false

## R24: NOTATION_ibd (Block)
- ELEMENT_SERVER_ID: 96de18c2-8e29-46b8-ae68-5eed1364da50
- isEncapsulated: false

## R25 (Arrow to Right)

## R26: Systems Engineering Process (Rectangle with Text)

## R27: Welche Anforderungen ergeben sich? Welche weiteren Anforderungen ergeben sich aus Konzeptentscheidungen? Welchen Input muss mir der Stakeholder liefern? (Arrow Down)

## R28: Wer ist mein Stakeholder und was ist sein Use Case? (Arrow Down)

## R29: Wie kann ich nachweisen, dass mein System die Anforderungen erfüllt? (Arrow Down)

## R30: Wie sieht mein System zur Erfüllung der Use Cases aus? (Arrow Down)

## R31: Data_Package (Block)

## R32: ElektrischerBasistype (Block)

## R33: Gen Electric Motor (Block)
- Generalization -> R32
- Generalization -> R34

## R34: Gen Motor (Block)
- Generalization -> R59

## R35: Gen Battery (Block)
- Generalization -> R59
- Generalization -> R32

## R36: GeometrischerBasistype (Block)

## R37: Li-Ion Battery (Block)
- Generalization -> R35
- Satisfy -> 9

## R38: Controller (Block)
- Generalization -> R59
- Generalization -> R32

## R39: RoboClaw_Motor_Controller (Block)
- Satisfy -> 9
- realizes -> R143
- Satisfy -> 25
- realizes -> R144
- Generalization -> R32
- Generalization -> R38
- Satisfy -> 8
- realizes -> R141

## R40: Custom_Encoder_Voltage_Divider_PCB (Block)
- Generalization -> R32
- realizes -> R143
- realizes -> R144

## R41: Custom_Serial_Splitter_PCB (Block)
- realizes -> R143
- Generalization -> R32
- realizes -> R144

## R42: Harness Body Assembly (Block)
- Satisfy -> 8

## R43: Harness Head (Block)
- realizes -> R144

## R44: Harness Rocker-Bogie (Block)

## R45: LED_Array (Block)
- Generalization -> R32

## R46: Logic Shifter (Block)
- realizes -> R143
- Generalization -> R32

## R47: A (Interface Block)

## R48: Drive Motor (Block)
- realizes -> R141
- Generalization -> R51
- Satisfy -> 1.1.3.4

## R49: Encoder (Block)
- Generalization -> R32

## R50: Gear (Block)

## R51: Gen Gearmotor with Encoder (Block)
- Generalization -> R59
- Association -> R49
- Association -> R50
- Association -> R52

## R52: Motor (Block)
- Generalization -> R33

## R53: Steering Motor (Block)
- Generalization -> R51

## R54: Raspberry Pi (Block)
- Generalization -> R32
- realizes -> R142
- realizes -> R144
- realizes -> R143

## R55: Switch (Block)
- realizes -> R144
- Generalization -> R32

## R56: 5V Regulator (Block)
- Generalization -> R32
- Satisfy -> 8
- Generalization -> R57
- Satisfy -> 9

## R57: Gen Voltage Regulator (Block)
- Generalization -> R59
- Generalization -> R32

## R58: Voltmeter (Block)
- Generalization -> R32
- realizes -> R144

## R59: MechanischerBasistype (Block)

## R60: Head Housing (Block)

## R61: Housing Body Assembly (Block)

## R62: Struts (Block)

## R63: Gen Wheel (Block)
- Generalization -> R59

## R64: Wheel (Block)
- Generalization -> R63
- realizes -> R141
- Association -> R5
- Satisfy -> 1.1.3.4

## R65: Data_Port (Block)

## R66: Drehzahl Sensor (Block)
- Generalization -> R80

## R67: Electrical_Power_Port (Block)

## R68: FMI_Port (Block)

## R69: Force_Port (Block)
- Generalization -> R78

## R70: Gravitationsfeld (Block)
- Generalization -> R78

## R71: Connector to Body (Block)

## R72: Head Connector (Block)

## R73: Head Connector B_Ass (Block)

## R74: Mount_Port (Block)

## R75: Rocker-Bogie Front Connector (Block)

## R76: Rocker-Bogie Middle Connector (Block)

## R77: Physical (Block)

## R78: Physical _Port (Block)

## R79: Rotation_Port (Block)
- Generalization -> R78

## R80: Sensor (Block)
- Generalization -> R65

## R81: Sensorquelle_Port (Block)
- Generalization -> R65

## R82: Control software (Block)

## R83: Mobile App (Block)

## R84: Bouncing (logicalArchitecture)
- Generalization -> R141

## R85: Driving (logicalArchitecture)
- Generalization -> R141

## R86: Flying (logicalArchitecture)
- Generalization -> R141

## 25: Motor und Encoder Spannung (Requirement)
Der Motor des Drive Motors benötigt eine Spannung von 12V und der Encoder eine Spannung von 5V.
- Trace -> 1.1.3.4
- Trace -> 9

## 8: Energieverteilung (Requirement)
Der Rover soll die Energie an die internen Verbraucher verteilen

## 9: Korrekte Stromgrößen (Requirement)
Der Rover soll die korrekte Spannung und den korrekten Strom für die internen Verbraucher zu Verfügung stellen

## 21: Anfahren (Requirement)
Der Rover muss anfahren können

## 24: Bremsen (Requirement)
Der Rover muss in der Lage sein zum Stillstand zu kommen

## 11: Elektrischer Antrieb (Requirement)
Der Rover soll für die Fortbewegung einen elektrischen Antrieb verwenden

## 11.1: Fortbewegung Elektromotor (Requirement)
Der Rover soll für den zur Fortbewegung nötigen Antrieb Elektromotoren verwenden

## 22: Geschwindigkeit (Performance Requirement)
Der Rover muss eine Geschwindigkeit von 0.2 m/s auf ebenem Grund erreichen können.
- Trace -> 1.1.3.1

## 23: Strecke (Requirement)
Der Rover muss mindestens 100 m pro Tag auf ebenem Untergrund zurücklegen können.
- Trace -> 1.1.3.1

## 6: LED Anzeige (Requirement)
Der Rover soll eine LED Anzeige besitzen die Auskunft darüber gibt ob der Rover ein- oder ausgeschaltet ist
- DeriveReqt -> 1.1.1.1

## 13: Geschwindigkeitsändeung durchführen (Requirement)
Der Rover soll seine Geschwindigkeit ändern können

## 14: Richtungsänderung durchführen (Requirement)
Der Rover soll seine Fahrtrichtung ändern können

## 1: Sammlung Anforderungen zum Rover (Requirement)

## 1.1: Sammlung aller technischen Anforderungen (Requirement)

## 1.1.2: Energieversorgung (Requirement)
Der Rover muss über eine Energieversorgung verfügen

## 1.1.2.3: Elektrische interne Energiequelle (Requirement)
Der Rover soll ausschließlich über eine elektrische interne Energieversorgung verfügen
- DeriveReqt -> 9
- DeriveReqt -> 11
- DeriveReqt -> 8

## 1.1.2.1: Externe Energieversogung (Requirement)
Der Rover soll ohne permante externe Energieversogung betrieben werden

## 1.1.2.2: Interne Energieversogung (Requirement)
Der Rover soll über eine zentrale interne Energieversorgung verfügen

## 1.1.2.2.2: Verfügbare Leistung (Requirement)
Durch die interne Energieversorgung soll der Rover mindestens 4 Stunden lang betrieben werden können

## 1.1.2.2.1: Wiederladbarkeit (Requirement)
Der Rover soll über eine wiederladbare interne Energieversorgung verfügen

## 1.1.3: Fortbewegung (Requirement)
Der Rover muss in der Lage sein sich selbstständig fortzubewegen
- DeriveReqt -> 11

## 1.1.3.1: Fortbewegung auf ebenem Grund (Requirement)
Der Rover muss in der Lage sein sich selbstständig auf ebenem Grund fortzubewegen
- Trace -> 23
- DeriveReqt -> 22
- DeriveReqt -> 21

## 1.1.3.4: Fortbewegung durch Räder (Requirement)
Der Rover soll sich selbstständig durch Fahren mit Rädern fortbewegen.
- Trace -> 1.1.3

## 1.1.3.2: Fortbewegung über Hindernisse (Requirement)
Der Rover muss in der Lage sein, über ein Hindernis mit einer maximalen Größe von 20cm Durchmesser fortzubewegen

## 1.1.3.3: Fortbewegung über Steigungen (Requirement)
Der Rover muss in der Lage sein sich selbstständig über Steigungen bis maximal 15° fortzubewegen

## 1.1.6: Gesamtmasse (Requirement)
Die Gesamtmasse des Rovers darf 10 kg nicht überschreiten

## 1.1.5: Optisches Feedback (Requirement)
Der Rover soll ein optisches Feedback darüber geben ob er ein- oder ausgeschaltet ist
- DeriveReqt -> 6

## 1.1.4: Steuerbarkeit (Requirement)
Der Rover soll von steuerbar sein

## 1.1.4.1: Steuerbarkeit von außen (Requirement)
Der Rover soll von von außen steuerbar sein

## 1.1.4.1.1: Geschwindigkeitsändeung vorgeben (Requirement)
Dem Rover soll von außen eine Änderung seiner Geschwindigkeit vorgeben werden können
- DeriveReqt -> 13

## 1.1.4.1.2: Richtungsänderung vorgeben (Requirement)
Dem Rover soll von außen eine Änderung seiner Fahrtrichtung vorgeben werden können
- DeriveReqt -> 14

## 1.1.1: Struktur (Requirement)
Der Rover muss eine mechanische Struktur besitzen

## 1.1.1.1: Roverkopf (Requirement)
Der Rover soll einen "Kopf" besitzen in dem die LED Anzeige untergebracht ist

## 1.2: Sammlung gesetzlicher Anforderungen (Requirement)

## R121: Kontext Umwelt (Block)
- Association -> R174
- Association -> R146

## R122: FMI_5V_Regulator (Block)
- Generalization -> R56

## R123: FMI_Battery (Block)
- Generalization -> R37

## R124: FMI_Custom_Encoder_Voltage_Divider_PCB (Block)
- Generalization -> R40

## R125: FMI_Custom_Serial_Splitter_PCB (Block)
- Generalization -> R41

## R126: FMI_Drive_Motor (Block)
- Generalization -> R48
- Generalization -> R129

## R127: FMI_Encoder (Block)
- Generalization -> R49

## R128: FMI_Gear (Block)
- Generalization -> R50

## R129: FMI_Gearmotor_with_encoder (Block)
- Association -> R128
- Association -> R132
- Association -> R127

## R130: FMI_LED_Array (Block)
- Generalization -> R45

## R131: FMI_Logic_Shifter_PCB (Block)
- Generalization -> R46

## R132: FMI_Motor (Block)
- Generalization -> R52

## R133: FMI_Raspberry_pi (Block)
- Generalization -> R54

## R134: FMI_RoboClaw_Motor_Controller (Block)
- Generalization -> R39

## R135: FMI_Steering_Motor (Block)
- Generalization -> R129

## R136: FMI_Switch (Block)
- Generalization -> R55

## R137: FMI_Voltmeter (Block)
- Generalization -> R58

## R138: FMI_Wheel (Block)
- Generalization -> R64

## R139: FMI_Simulationsmodell (Block)
- Association -> R136
- Association -> R138
- Association -> R134
- Association -> R130
- Association -> R125
- Association -> R126
- Association -> R173
- Association -> R131
- Association -> R173
- Association -> R138
- Association -> R126
- Association -> R173
- Association -> R134
- Association -> R173
- Association -> R137
- Association -> R173
- Association -> R122
- Association -> R134
- Association -> R138
- Association -> R135
- Association -> R124
- Association -> R133
- Association -> R126
- Association -> R126
- Association -> R126
- Association -> R173
- Association -> R123
- Association -> R126
- Association -> R134
- Association -> R135
- Association -> R135
- Association -> R138
- Association -> R135
- Association -> R138
- Association -> R138
- Association -> R134

## R140: Mars Rover Logical (logicalArchitecture)
- Association -> R145
- Association -> R144
- Association -> R85
- Association -> R142
- Association -> R143

## R141: Change of Location (logicalArchitecture)

## R142: Communication (logicalArchitecture)

## R143: Control and Data Handling (logicalArchitecture)

## R144: Energy Supply (logicalArchitecture)

## R145: Probe Handling (logicalArchitecture)

## R146: Mars Rover (System)
- Association -> R150
- Association -> R165
- Association -> R165
- Association -> R165
- Association -> R165
- Association -> R155
- Association -> R155
- Association -> R161
- Association -> R162
- Association -> R168
- Association -> R180
- Association -> R162
- Association -> R168
- Association -> R160
- Association -> R175
- realizes -> R140
- Association -> R168
- Association -> R180
- Association -> R165
- Association -> R165
- Association -> R168
- Association -> R155
- Association -> R180
- Association -> R155

## R147 (Legend)

## R148: DATA LEGEND (Legend)

## R149: Voltage Legend (Legend)

## R150: Body Assembly (Block)
- Association -> R55
- Association -> R37
- Association -> R73
- Association -> R153
- Association -> R58
- Association -> R61
- Association -> R8
- Association -> R42
- Association -> R151
- Association -> R154

## R151: Differntial Pivot Connector B_Ass (Block)

## R152: Electronics Board (Block)

## R153: Electronics Board Assembly (Block)
- Association -> R39
- Association -> R152
- Association -> R39
- Association -> R39
- Association -> R56
- Association -> R82
- Association -> R40
- Association -> R39
- Association -> R54
- Association -> R39
- Association -> R41

## R154: Rocker-Bogie Connector B_Ass (Block)

## R155: Corner Steering Assembly (Block)
- Association -> R159
- Association -> R157
- Association -> R156
- Association -> R53
- Association -> R158
- Association -> R8

## R156: Corner Steering Harness (Block)

## R157: Corner Steering Motor Mount (Block)

## R158: Corner Steering Shaft Coupler (Block)

## R159: Encoder Mount (Block)

## R160: Differential Pivot Assembly (Block)
- Association -> R71
- Association -> R62
- Association -> R8

## R161: Head Assembly (Block)
- Association -> R46
- Association -> R72
- Association -> R45
- Association -> R43
- Association -> R60
- Association -> R8

## R162: Rocker-Bogie Assembly (Block)
- Association -> R163
- Association -> R75
- Association -> R76
- Association -> R164
- Association -> R8
- Association -> R44

## R163: Rocker-Bogie Joint (Block)

## R164: Rocker-Bogie Rear/Main Connector (Block)

## R165: Base Wheel Assembly (Block)
- Association -> R48
- Association -> R166
- Association -> R64
- Association -> R8

## R166: Drive Motor Mount (Block)

## R167: Connecting Channel (Block)

## R168: Corner Wheel Assembly (Block)
- Association -> R169
- Association -> R167
- Association -> R8
- Association -> R170

## R169: Hard Stop Mount (Block)

## R170: Harness Corner Wheel (Block)

## R171: System (Block)
- Association -> R146
- Association -> R172

## R172: Mobile Device (Block)
- Association -> R83

## R173: FMI_Untergrund (Block)
- Generalization -> R183

## R174: Umwelt (Block)
- Association -> R177

## R175: Atmosphäre (Block)

## R176: Gesteinsprobe (Block)
- Generalization -> R181

## R177: Himmelskörper (Block)
- Association -> R175
- Association -> R180

## R178: Hindernis (Block)
- Generalization -> R181

## R179: Mars (Block)
- Generalization -> R177

## R180: Oberfläche (Block)
- Association -> R183
- Association -> R183
- Association -> R183
- Association -> R183
- Association -> R181
- Association -> R181
- Association -> R183
- Association -> R183

## R181: Objekt (Block)
- Association -> R183

## R182: Sonne (Block)
- Generalization -> R177

## R183: Untergrund (Block)

## R184: Anwendungsfall Viewpoint (Viewpoint)

## R185: Simulations Viewpoint (Viewpoint)

## R186: Systems Engineering Viewpoint (Viewpoint)

## R187: Test Viewpoint (Viewpoint)

## ERC: ERC Requirements (Requirement)
Root Requirement for all ERC Requirements.

## ERC_3: System Requirements (Requirement)
Each rover must be compliant with requirements listed below to take part in the challenge. Special cases of non-compliance should be discussed with organiser as soon as possible in development process. Organiser has right to exclude team from field trials especially when non-compliances are reported too late (e.g. during challenge event). It is highly recommended that teams present status of compliance with specified requirements within Technical Reports in highly transparent way.

## ERC_2_6: Communication (Requirement)

## ERC_2_6_2: Accepted frequencies (Requirement)
Frequencies for radio amateur bands, WiFi and ISM bands

## ERC_2_6_2_3: ISM bands (Requirement)
It is possible to use ISM bands within their limitations but team must designate which rule is in compliance with Polish regulations (http://prawo.sejm.gov.pl/isap.nsf/download.xsp/WDU20140001843/O/D20141843.pdf).
ERC does not accept ISM bands which are not accepted in Poland (e.g. 915 MHz).
Voice communication using 500 mW PMR licensed transceiver is allowed on following channel frequencies (MHz):
1. 446,00625
2. 446,01875
3. 446,03125
4. 446,04375
5. 446,05625
6. 446,06875
7. 446,08125 - reserved for organising team
8. 446,09375 - reserved for organising team

## ERC_2_6_2_4: Other frequencies (Requirement)
Other frequencies are allowed only when relevant licence valid on venue territory is presented by the team. Those communication channels must be described in documentation and agreed with organisers.

## ERC_2_6_2_1: Radio amateur bands (Requirement)
Accepted bands up to 1 W signal transmitted and up 10 W EIRP.
144 - 146 MHz
430 - 440 MHz
1240 - 1300 MHz
5650 - 5850 MHz
It is highly recommended that each team should have at least one member with radio amateur license (CEPT class T/R 61-01).

## ERC_2_6_2_2: WiFi (Requirement)
At 2.4 and 5 GHz WiFi bands only WiFi communication standard is accepted. Any other systems like analog video cameras or RC controllers using frequencies 2412-2472 Mhz and 5260-5700 MHz are forbidden.
For 2.4GHz:
- accepted channels: 1-13 (2412 MHz – 2472 MHz);
- up to 100 mW EIRP;
- accepted standards: 802.11b/g (802.11n forbidden);
- Rover can use only one 20 MHz channel.
For 5GHz
- accepted channels: 52, 56, 60, 64, 100, 104, 108, 112, 116, 120, 124, 128, 132, 136, 140 (5260 MHz – 5700 MHz)
- up to 100 mW EIRP.
- accepted standards: 802.11a/h/n (802.11ac forbidden);
- Rover can use only one 40 MHz channel.
WiFi SSID should be set to “_teamname”.
Channels will be assigned by judge during RF check before each task attempt.

## ERC_2_6_1: General (Requirement)
Radio communication with the rover has to use legally available frequencies and power levels. It is expected that maximum distance between rover and antenna mast would be less than 100 m. Direct line-of-sight between control base and rover antennas can be occluded by different forms of terrain morphology.

## ERC_2_6_3: Radio Frequency Form (Requirement)
Each Team must fill Radio Frequency Form for every RF module used. It shall be included in relevant Technical Reports as an appendix (see documentation specification). If these documents are not submitted in the requested form, team will not be allowed to participate in the Challenge.
RF Form shall contain:
a) Team name;
b) Country;
c) Name of the person responsible for communication system;
d) Contact to the person responsible for communication system (e-mail address);
e) Photo of the rover;
f) Photo of the ground station;
g) Number of different communication systems;
h) System information (this part should be filled for every RF system):
● RF system name;
● Short description;
● Frequency;
● Bandwidth;
● RF power (output power + EIRP);
● Modulation;
● Antennas on rover and ground station - models, radiation patterns (see Pic 1 as example), pictures
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
## ERC_2_1: General Requirements (Requirement)
The rover has to be a standalone, mobile platform. No cables or tethers are allowed for connection to external data links or power sources during its operation.
Teams should design and build their own rover, but COTS (Commercial-Off-The-Shelf) components are allowed and recommended. COTS rover platform would be considered, but all such applications will be discussed separately to ensure that competition is fair play.

## ERC_2_4: Rover Autonomy (Requirement)
Rover autonomy or capabilities of automation of particular tasks are highly recommended to be presented during competition trials. They can provide major advantage in scoring for all the tasks.
In automated control, states and commands defined below should be differentiated:
● “ start ” command - command to be send at the beginning of the attempt;
● “ working ” state - nominal work during attempt;
● “ wait ” command - enter “ wait ” state. Team can use it at any time for sensor readings stabilization;
● ” waiting ” state - rover should wait still for “ resume ” command. This state should be automatically entered if rover reaches task check-point. System should be prepared that during this state sensors can be obstructed by judge or team members presence in rover vicinity (e.g. checking distance to the check-point). Operator cannot influence a system during this state. Reaching this state do not stop task time;
● “ resume ” command - transition from “ waiting ” to “ working ” state;
● “ stop ” - rover immediate stop - control can be switched to manual.
Above list is not exhaustive and teams can define additional states and commands.
In order to achieve points for autonomy or single task automation, teams cannot touch the controls once the attempt begins. The only exception is to send commands listed above. If team members touch the controls, then the autonomy points for that attempt will not be awarded. However, at any point teams may switch to manual control to complete the task tele-operating rover. Telemetry to monitor the rover operation should be monitored during autonomous/automatic operations and its recording and open access sharing after the event is highly recommended but not mandatory.
In autonomy mode extra safety precautions should be taken. Minimum requirements are specified in Rover Safety section of this document.

## ERC_2_3: Rover Control and Operations (Requirement)
The rover maximum speed cannot be greater than 0.5 m/s.
Team should be able to control rover via radio link in real time. Each Task will require the rover to travel a certain distance, but never more than 100m from the starting point. The starting point will be no farther than 50 meters from the antenna mast. All communication equipment, including antennas, should be deployed in vicinity of control station. Teams should be prepared to place antenna mast maximum 20m from control station location.
The rover should be built to handle challenging terrain, appropriate dust and general weather conditions resistance described in FIeld Trials section. Operational temperature range should be between +10 and +30 degrees Celsius.

## ERC_2_5: Rover Safety (Requirement)

## ERC_2_5_2: Activity Indicator (Requirement)
Rover should be equipped with indicator lamp informing about readiness to receive commands.

## ERC_2_5_2_3: Indicator Colors (Requirement)
Recommended colours are: yellow, orange or red

## ERC_2_5_2_5: Indicator Operation (Requirement)
Activity indicator lamp should be active for 5 seconds before any rover operation is executed. During this time rover should be completely still and safe.

## ERC_2_5_2_2: Indicator Use (Requirement)
It should be active in any case when rover is ready to move (drive or e.g. operate manipulator).

## ERC_2_5_2_1: Indicator Visibility (Requirement)
Indicator should be clearly visible from at least 10m attracting attention of people in vicinity by blinking or flashing.

## ERC_2_5_2_4: Industrial Grade (Requirement)
It is highly recommended to use industrial grade device.

## ERC_2_5_3: Automatic/Autonomous Functionality (Requirement)

## ERC_2_5_3_2: Overflow (Requirement)
By all means teams should prevent overflowing any communication/interface buffers or keeping commanding rover or its subsystems when should be still or deactivated to avoid situations when immediate or rapid movement is executed after system activation or commanding.

## ERC_2_5_3_1: Starting Delay (Requirement)
Any autonomous or automatic operation should start with delay of at least 5 seconds after activation.

## ERC_2_5_1: Emergency Stop (Requirement)
The Rover shall be equipped with an easily accessible red emergency stop button.

## ERC_2_5_1_6: Button Accessability (Requirement)
If an unsafe event occurs, judges must be able to access button and deactivate rover without any additional actions necessary.

## ERC_2_5_1_5: Button Operation (Requirement)
Operation must be possible by open hand hit.

## ERC_2_5_1_4: Physical Button (Requirement)
Even if RF certified EM button is in use at least one physical emergency button must be placed on the rover construction.

## ERC_2_5_1_1: Robustness (Requirement)
Button mounting should withstand hard hit and should be attached to stiff element of rovers body.

## ERC_2_5_1_3: Saftey Circuit (Requirement)
The emergency stop button must be part of highly reliable circuit, which action is to isolate the batteries from the system by single button hit unitl procedure is executed.

## ERC_2_5_1_2: Used Parts (Requirement)
An unmodified, industrial, commercial-off-the-shelf, emergency stop button and other parts of safety circuit are required.

## ERC_2_2: System Weight (Requirement)
The suggested rover weight is 50kg. The limitation applies to every Task (i.e. task-relevant rover configuration) separately. Equipment used for rover maintenance and preparation, unused spare parts, and elements not mounted during a particular Task are not included in this limit.
There is no weight limit on equipment used to steer and control the rover from the rover control area, communications equipment in that area or maintenance equipment.
Rover lighter than limit will be rewarded and heavier penalised by number of points defined in scoring rules in appendix to this document.

## ERC_5.5: Tasks Requirements (Requirement)

## ERC_1_1: Science Task Requirements (Requirement)
Root Requirement for the Science Task.

## ERC_1_1_9: Container Removing (Requirement)
Containers can be manipulated and removed from the robot only in the company of judge.

## ERC_1_1_2: Deep Sample (Requirement)
Deep sample should at least contain material from the deepest reached point. In ideal scenario team should present unmixed, undisturbed cross-section of all layers from the surface to the deepest reached point.
The deep sample should be clearly visible in undisturbed state at least before the sample is placed into the container. It is possible to leave detached part of sampling device inside container but ideally only deepest part of the sample should be placed into container (not mixed with upper layers of soil).

## ERC_1_1_10: Deep Sampling Device (Requirement)
Deep sampling device should be prepared to handle materials from loose soil to hard gypsum.

## ERC_1_1_6: Image Resolution (Requirement)
Minimum resolution of the images is 800x600 pixels. Object of the image (sample location or sample itself) should occupy major part of the image. Image quality should be reasonable for scientific needs.

## ERC_1_1_8: One Container for one Sample (Requirement)
Samples should be delivered in dedicated containers, one container for each sample

## ERC_1_1_17: Preventing Sample Exposure (Requirement)
Extra points could be awarded if deep sample caching is done without sample exposure to above-surface conditions

## ERC_1_1_3: Real Design (Requirement)
Container design and sample insertion method/device should be inspired by real missions requirements

## ERC_1_1_7: Sample Container (Requirement)
Rover must be equipped with at least one sample container.

## ERC_1_1_14: Sample Weight (Requirement)
each sample should weight at least 25g and preferably 50-100g according to scoring.

## ERC_1_1_5: Sampling Device (Requirement)
The rover should be equipped with at least one sampling device.

## ERC_1_1_13: Separation of reaction forces (Requirement)
The method for sampling reaction forces/torques separation from rover body should be presented and will be scored by judge based on operation observation.

## ERC_1_1_1: Soil (Requirement)
The system shall be able to handle multiple layers of different soil.

## ERC_1_1_15: Stored data (Requirement)
All data stored at least until reviewed by the judge

## ERC_1_1_12: Storing physical parameters (Requirement)
Any additional physical parameters must be documented in the control station and stored till judge inspection after task attempt end. Judge will evaluate quality of received data.

## ERC_1_1_11: Surface Sampling Device (Requirement)
Surface sampling device should be prepared to handle different type of loose soil.

## ERC_1_1_4: Trench Design (Requirement)
The trench should have minimum 30cm length, minimum 5cm depth and at least one wall steep enough to present clearly visible soil layers. This findings should be documented on a photo.

## ERC_1_1_16: Use of innovative Design (Requirement)
Presentation of innovative methods of samples extraction (e.g. device design, operation, way to mitigate transfer/elimination of reaction forces/torques to rover body etc.), measurements (custom made sensors design, sample preparation and interaction methods) and caching (including cache design specifics).

## 3: ERC Requirements (Requirement)
Root Requirement for all ERC Requirements.

## 3_1: System Requirements (Requirement)
Each rover must be compliant with requirements listed below to take part in the challenge. Special cases of non-compliance should be discussed with organiser as soon as possible in development process. Organiser has right to exclude team from field trials especially when non-compliances are reported too late (e.g. during challenge event). It is highly recommended that teams present status of compliance with specified requirements within Technical Reports in highly transparent way.

## 3_1_6: Communication (Requirement)

## 3_1_6_2: Accepted frequencies (Requirement)
Frequencies for radio amateur bands, WiFi and ISM bands

## 3_1_6_2_3: ISM bands (Requirement)
It is possible to use ISM bands within their limitations but team must designate which rule is in compliance with Polish regulations (http://prawo.sejm.gov.pl/isap.nsf/download.xsp/WDU20140001843/O/D20141843.pdf).
ERC does not accept ISM bands which are not accepted in Poland (e.g. 915 MHz).
Voice communication using 500 mW PMR licensed transceiver is allowed on following channel frequencies (MHz):
1. 446,00625
2. 446,01875
3. 446,03125
4. 446,04375
5. 446,05625
6. 446,06875
7. 446,08125 - reserved for organising team
8. 446,09375 - reserved for organising team

## 3_1_6_2_4: Other frequencies (Requirement)
Other frequencies are allowed only when relevant licence valid on venue territory is presented by the team. Those communication channels must be described in documentation and agreed with organisers.

## 3_1_6_2_1: Radio amateur bands (Requirement)
Accepted bands up to 1 W signal transmitted and up 10 W EIRP.
144 - 146 MHz
430 - 440 MHz
1240 - 1300 MHz
5650 - 5850 MHz
It is highly recommended that each team should have at least one member with radio amateur license (CEPT class T/R 61-01).

## 3_1_6_2_2: WiFi (Requirement)
At 2.4 and 5 GHz WiFi bands only WiFi communication standard is accepted. Any other systems like analog video cameras or RC controllers using frequencies 2412-2472 Mhz and 5260-5700 MHz are forbidden.
For 2.4GHz:
- accepted channels: 1-13 (2412 MHz – 2472 MHz);
- up to 100 mW EIRP;
- accepted standards: 802.11b/g (802.11n forbidden);
- Rover can use only one 20 MHz channel.
For 5GHz
- accepted channels: 52, 56, 60, 64, 100, 104, 108, 112, 116, 120, 124, 128, 132, 136, 140 (5260 MHz – 5700 MHz)
- up to 100 mW EIRP.
- accepted standards: 802.11a/h/n (802.11ac forbidden);
- Rover can use only one 40 MHz channel.
WiFi SSID should be set to “_teamname”.
Channels will be assigned by judge during RF check before each task attempt.

## 3_1_6_1: General (Requirement)
Radio communication with the rover has to use legally available frequencies and power levels. It is expected that maximum distance between rover and antenna mast would be less than 100 m. Direct line-of-sight between control base and rover antennas can be occluded by different forms of terrain morphology.

## 3_1_6_3: Radio Frequency Form (Requirement)
Each Team must fill Radio Frequency Form for every RF module used. It shall be included in relevant Technical Reports as an appendix (see documentation specification). If these documents are not submitted in the requested form, team will not be allowed to participate in the Challenge.
RF Form shall contain:
a) Team name;
b) Country;
c) Name of the person responsible for communication system;
d) Contact to the person responsible for communication system (e-mail address);
e) Photo of the rover;
f) Photo of the ground station;
g) Number of different communication systems;
h) System information (this part should be filled for every RF system):
● RF system name;
● Short description;
● Frequency;
● Bandwidth;
● RF power (output power + EIRP);
● Modulation;
● Antennas on rover and ground station - models, radiation patterns (see Pic 1 as example), pictures
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
## 3_1_1: General Requirements (Requirement)
The rover has to be a standalone, mobile platform. No cables or tethers are allowed for connection to external data links or power sources during its operation.
Teams should design and build their own rover, but COTS (Commercial-Off-The-Shelf) components are allowed and recommended. COTS rover platform would be considered, but all such applications will be discussed separately to ensure that competition is fair play.

## 3_1_4: Rover Autonomy (Requirement)
Rover autonomy or capabilities of automation of particular tasks are highly recommended to be presented during competition trials. They can provide major advantage in scoring for all the tasks.
In automated control, states and commands defined below should be differentiated:
● “ start ” command - command to be send at the beginning of the attempt;
● “ working ” state - nominal work during attempt;
● “ wait ” command - enter “ wait ” state. Team can use it at any time for sensor readings stabilization;
● ” waiting ” state - rover should wait still for “ resume ” command. This state should be automatically entered if rover reaches task check-point. System should be prepared that during this state sensors can be obstructed by judge or team members presence in rover vicinity (e.g. checking distance to the check-point). Operator cannot influence a system during this state. Reaching this state do not stop task time;
● “ resume ” command - transition from “ waiting ” to “ working ” state;
● “ stop ” - rover immediate stop - control can be switched to manual.
Above list is not exhaustive and teams can define additional states and commands.
In order to achieve points for autonomy or single task automation, teams cannot touch the controls once the attempt begins. The only exception is to send commands listed above. If team members touch the controls, then the autonomy points for that attempt will not be awarded. However, at any point teams may switch to manual control to complete the task tele-operating rover. Telemetry to monitor the rover operation should be monitored during autonomous/automatic operations and its recording and open access sharing after the event is highly recommended but not mandatory.
In autonomy mode extra safety precautions should be taken. Minimum requirements are specified in Rover Safety section of this document.

## 3_1_3: Rover Control and Operations (Requirement)
The rover maximum speed cannot be greater than 0.5 m/s.
Team should be able to control rover via radio link in real time. Each Task will require the rover to travel a certain distance, but never more than 100m from the starting point. The starting point will be no farther than 50 meters from the antenna mast. All communication equipment, including antennas, should be deployed in vicinity of control station. Teams should be prepared to place antenna mast maximum 20m from control station location.
The rover should be built to handle challenging terrain, appropriate dust and general weather conditions resistance described in FIeld Trials section. Operational temperature range should be between +10 and +30 degrees Celsius.

## 3_1_5: Rover Safety (Requirement)

## 3_1_5_2: Activity Indicator (Requirement)
Rover should be equipped with indicator lamp informing about readiness to receive commands.

## 3_1_5_2_3: Indicator Colors (Requirement)
Recommended colours are: yellow, orange or red

## 3_1_5_2_5: Indicator Operation (Requirement)
Activity indicator lamp should be active for 5 seconds before any rover operation is executed. During this time rover should be completely still and safe.

## 3_1_5_2_2: Indicator Use (Requirement)
It should be active in any case when rover is ready to move (drive or e.g. operate manipulator).

## 3_1_5_2_1: Indicator Visibility (Requirement)
Indicator should be clearly visible from at least 10m attracting attention of people in vicinity by blinking or flashing.

## 3_1_5_2_4: Industrial Grade (Requirement)
It is highly recommended to use industrial grade device.

## 3_1_5_3: Automatic/Autonomous Functionality (Requirement)

## 3_1_5_3_2: Overflow (Requirement)
By all means teams should prevent overflowing any communication/interface buffers or keeping commanding rover or its subsystems when should be still or deactivated to avoid situations when immediate or rapid movement is executed after system activation or commanding.

## 3_1_5_3_1: Starting Delay (Requirement)
Any autonomous or automatic operation should start with delay of at least 5 seconds after activation.

## 3_1_5_1: Emergency Stop (Requirement)
The Rover shall be equipped with an easily accessible red emergency stop button.

## 3_1_5_1_6: Button Accessability (Requirement)
If an unsafe event occurs, judges must be able to access button and deactivate rover without any additional actions necessary.

## 3_1_5_1_5: Button Operation (Requirement)
Operation must be possible by open hand hit.

## 3_1_5_1_4: Physical Button (Requirement)
Even if RF certified EM button is in use at least one physical emergency button must be placed on the rover construction.

## 3_1_5_1_1: Robustness (Requirement)
Button mounting should withstand hard hit and should be attached to stiff element of rovers body.

## 3_1_5_1_3: Saftey Circuit (Requirement)
The emergency stop button must be part of highly reliable circuit, which action is to isolate the batteries from the system by single button hit unitl procedure is executed.

## 3_1_5_1_2: Used Parts (Requirement)
An unmodified, industrial, commercial-off-the-shelf, emergency stop button and other parts of safety circuit are required.

## 3_1_2: System Weight (Requirement)
The suggested rover weight is 50kg. The limitation applies to every Task (i.e. task-relevant rover configuration) separately. Equipment used for rover maintenance and preparation, unused spare parts, and elements not mounted during a particular Task are not included in this limit.
There is no weight limit on equipment used to steer and control the rover from the rover control area, communications equipment in that area or maintenance equipment.
Rover lighter than limit will be rewarded and heavier penalised by number of points defined in scoring rules in appendix to this document.

## 3_2: Tasks Requirements (Requirement)

## 3_2_1: Science Task Requirements (Requirement)
Root Requirement for the Science Task.

## 3_2_1_9: Container Removing (Requirement)
Containers can be manipulated and removed from the robot only in the company of judge.

## 3_2_1_2: Deep Sample (Requirement)
Deep sample should at least contain material from the deepest reached point. In ideal scenario team should present unmixed, undisturbed cross-section of all layers from the surface to the deepest reached point.
The deep sample should be clearly visible in undisturbed state at least before the sample is placed into the container. It is possible to leave detached part of sampling device inside container but ideally only deepest part of the sample should be placed into container (not mixed with upper layers of soil).

## 3_2_1_10: Deep Sampling Device (Requirement)
Deep sampling device should be prepared to handle materials from loose soil to hard gypsum.

## 3_2_1_6: Image Resolution (Requirement)
Minimum resolution of the images is 800x600 pixels. Object of the image (sample location or sample itself) should occupy major part of the image. Image quality should be reasonable for scientific needs.

## 3_2_1_8: One Container for one Sample (Requirement)
Samples should be delivered in dedicated containers, one container for each sample

## 3_2_1_17: Preventing Sample Exposure (Requirement)
Extra points could be awarded if deep sample caching is done without sample exposure to above-surface conditions

## 3_2_1_3: Real Design (Requirement)
Container design and sample insertion method/device should be inspired by real missions requirements

## 3_2_1_7: Sample Container (Requirement)
Rover must be equipped with at least one sample container.

## 3_2_1_14: Sample Weight (Requirement)
each sample should weight at least 25g and preferably 50-100g according to scoring.

## 3_2_1_5: Sampling Device (Requirement)
The rover should be equipped with at least one sampling device.

## 3_2_1_13: Separation of reaction forces (Requirement)
The method for sampling reaction forces/torques separation from rover body should be presented and will be scored by judge based on operation observation.

## 3_2_1_1: Soil (Requirement)
The system shall be able to handle multiple layers of different soil.

## 3_2_1_15: Stored data (Requirement)
All data stored at least until reviewed by the judge

## 3_2_1_12: Storing physical parameters (Requirement)
Any additional physical parameters must be documented in the control station and stored till judge inspection after task attempt end. Judge will evaluate quality of received data.

## 3_2_1_11: Surface Sampling Device (Requirement)
Surface sampling device should be prepared to handle different type of loose soil.

## 3_2_1_4: Trench Design (Requirement)
The trench should have minimum 30cm length, minimum 5cm depth and at least one wall steep enough to present clearly visible soil layers. This findings should be documented on a photo.

## 3_2_1_16: Use of innovative Design (Requirement)
Presentation of innovative methods of samples extraction (e.g. device design, operation, way to mitigate transfer/elimination of reaction forces/torques to rover body etc.), measurements (custom made sensors design, sample preparation and interaction methods) and caching (including cache design specifics).

## R288: dfdfdfdf (Block)
- Generalization -> R289

## R289: eereerere (Block)
- Association -> R290

## R290: rrerererer (Block)
- Association -> R288

## R291: Lichtsystem (Block)
- Association -> R292
- Association -> R293
- Association -> R292
- Association -> R294
- Association -> R294

## R292: Lampe (Block)

## R293: Nutzer (Block)

## R294: Schalter (Block)

## R295: Schalter if (Block)

## R296: Strom if (Block)

## R297: LampBulb (ImageSwitcher)

## R298: Lichtsystem (Simulation Configuration)

## R299: PowerButton (ImageSwitcher)

## R300: sys (Block)
- Association -> R301
- Association -> R302

## R301: empf (Block)

## R302: sender (Block)
