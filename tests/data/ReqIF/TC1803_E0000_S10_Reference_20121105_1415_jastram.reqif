# TC 1803 'HIS Exchange Process OEM -> SUP (third change)'

# Specification
- ReqIF.Name: Spec1

## R1: Obj-01
- A1: no change
- A2: no change
- E1: one

## R2: Obj-03
- A1: O3.A1 once
- A2: O3.A2 twice
- E1: two

## R3: Obj-04
- A1: no change
- A2: no change
- E1: one

## R4: Obj-05
- A1: no change
- A2: no change
- E1: one

# Specification
- ReqIF.Name: Spec2

## R5: Obj-08
- A1: no change
- A2: no change
- E1: one

## R6: Obj-09
- A1: no change
- A2: no change
- E1: one
